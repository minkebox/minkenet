--------------------------------------------------------------------------------

-- ----------------- Revision(Fill when without Release Note) -----------------
-- Date        	  Version    		Author         Chanage Description

-- 2015/11/27    V1.00.003              TRENDnet       Initial Release
--
-- 2016/12/16    V1.00.006              TRENDnet       Add igsQuerierVersion
--------------------------------------------------------------------------------
-- mib version: teg30284-1.00.022

	TEG-30284-MIB DEFINITIONS ::= BEGIN

IMPORTS 
	MODULE-IDENTITY, OBJECT-TYPE, NOTIFICATION-TYPE, 
	Gauge32, enterprises, IpAddress, Integer32, Unsigned32, TimeTicks, Counter32
													FROM SNMPv2-SMI 
	InetAddressType, InetAddress, InetAddressPrefixLength,
	InetScopeType
													FROM INET-ADDRESS-MIB                                                  
	InterfaceIndex,InterfaceIndexOrZero    
													FROM IF-MIB
	SnmpAdminString,SnmpEngineID,SnmpSecurityLevel 	FROM SNMP-FRAMEWORK-MIB 
	dot1dBridge, dot1dBasePortEntry, dot1dBasePort 	FROM BRIDGE-MIB                                                  
	RowStatus, TruthValue, DisplayString, 
	TEXTUAL-CONVENTION, MacAddress,TimeStamp, TimeInterval  FROM SNMPv2-TC;

	trendnet MODULE-IDENTITY
	    LAST-UPDATED "201504110000Z"
		ORGANIZATION "TRENDnet" 
		CONTACT-INFO "support@trendnet.com" 
        DESCRIPTION	 "The MIB module for management of TRENDnet series products."
		REVISION "201504110000Z"
         DESCRIPTION	 "The MIB module for management of TRENDnet series products."
		 ::= { enterprises 28866}

	products              		OBJECT IDENTIFIER ::= { trendnet 3 }
	teg30284				OBJECT IDENTIFIER ::= { products 1 }
	
VlanIndex ::= TEXTUAL-CONVENTION
    STATUS      current
    DESCRIPTION
        "A value used to index per-VLAN tables: values of 0 and
        4095 are not permitted; if the value is between 1 and
        4094 inclusive, it represents an IEEE 802.1Q VLAN-ID with
        global scope within a given bridged domain (see VlanId
        textual convention).  If the value is greater than 4095
        then it represents a VLAN with scope local to the
        particular agent, i.e. one without a global VLAN-ID
        assigned to it. Such VLANs are outside the scope of
        IEEE 802.1Q but it is convenient to be able to manage them
        in the same way using this MIB."
    SYNTAX      Unsigned32

VlanId ::= TEXTUAL-CONVENTION
    STATUS      current
    DESCRIPTION
        "A 12-bit VLAN ID used in the VLAN Tag header."
    SYNTAX      INTEGER (1..4094)

PortList ::= TEXTUAL-CONVENTION
    STATUS      current
    DESCRIPTION
        "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
    SYNTAX      OCTET STRING


BridgeId ::= TEXTUAL-CONVENTION
	STATUS  current
	DESCRIPTION
           "The Bridge-Identifier as used in the
           Spanning Tree
           Protocol to uniquely identify a bridge.  Its first two
           octets (in network byte order) contain a priority
           value and its last 6 octets contain the MAC address
           used to refer to a bridge in a unique fashion
           (typically, the numerically smallest MAC address
           of all ports on the bridge).
           Several objects in this MIB module represent values of
           timers used by the Spanning Tree Protocol.  In this
           MIB, these timers have values in units of hundreths of
           a second (i.e. 1/100 secs).
           These timers, when stored in a Spanning Tree Protocol's
           BPDU, are in units of 1/256 seconds.  Note, however,
           that 802.1D-1990 specifies a settable granularity of
           no more than 1 second for these timers.  To avoid
           ambiguity, a data type is defined here as a textual
           convention and all representation of these timers
           in this MIB module are defined using this data type.  An
           algorithm is also defined for converting between the
           different units, to ensure a timer's value is not
		   distorted by multiple conversions."
	SYNTAX          OCTET STRING (SIZE (8))
     
Timeout ::= TEXTUAL-CONVENTION
	DISPLAY-HINT "d4"
	STATUS       current
	DESCRIPTION
           "A STP timer in units of 1/100 seconds
           
            To convert a Timeout value into a value in units of
            1/256 seconds, the following algorithm should be used:
           
                 b  = floor( (n * 256) / 100)
            
            where:
                 floor   =  quotient [ignore remainder]
                 n is the value in 1/100 second units
                 b is the value in 1/256 second units
                 To convert the value from 1/256 second units back to
				 1/100 seconds, the following algorithm should be used:
            
                 n = ceiling( (b * 100) / 256)
            
            where:
                  ceiling =  quotient [if remainder is 0], or
                             quotient + 1 [if remainder is non-zero]
                  n is the value in 1/100 second units
                  b is the value in 1/256 second units
             
             Note: it is important that the arithmetic operations are
             done in the order specified (i.e., multiply first, divide
             second)."
	SYNTAX       INTEGER

OwnerString ::= TEXTUAL-CONVENTION
	STATUS current
	DESCRIPTION
         "This data type is used to model an administratively
         assigned name of the owner of a resource. Implementations
         must accept values composed of well-formed NVT ASCII
         sequences. In addition, implementations should accept
         values composed of well-formed UTF-8 sequences.

         It is suggested that this name contain one or more of
         the following: IP address, management station name,
         network manager's name, location, or phone number.
         In some cases the agent itself will be the owner of
         an entry.  In these cases, this string shall be set
         to a string starting with 'monitor'.

         SNMP access control is articulated entirely in terms
         of the contents of MIB views; access to a particular
         SNMP object instance depends only upon its presence
         or absence in a particular MIB view and never upon
         its value or the value of related object instances.
         Thus, objects of this type afford resolution of
         resource contention only among cooperating
         managers; they realize no access control function
         with respect to uncooperative parties."
	SYNTAX OCTET STRING (SIZE (0..127))

EntryStatus ::= TEXTUAL-CONVENTION
	STATUS current
	DESCRIPTION
         "The status of a table entry.

         Setting this object to the value invalid(4) has the
         effect of invalidating the corresponding entry.
         That is, it effectively disassociates the mapping
         identified with said entry.
         It is an implementation-specific matter as to whether
         the agent removes an invalidated entry from the table.
         Accordingly, management stations must be prepared to
         receive tabular information from agents that corresponds
         to entries currently not in use.  Proper
         interpretation of such entries requires examination
         of the relevant EntryStatus object.

         An existing instance of this object cannot be set to
         createRequest(2).  This object may only be set to
         createRequest(2) when this instance is created.  When
         this object is created, the agent may wish to create
         supplemental object instances with default values
         to complete a conceptual row in this table.  Because the

         creation of these default objects is entirely at the option
         of the agent, the manager must not assume that any will be
         created, but may make use of any that are created.
         Immediately after completing the create operation, the agent
         must set this object to underCreation(3).

         When in the underCreation(3) state, an entry is allowed to
         exist in a possibly incomplete, possibly inconsistent state,
         usually to allow it to be modified in multiple PDUs.  When in
         this state, an entry is not fully active.
         Entries shall exist in the underCreation(3) state until
         the management station is finished configuring the entry
         and sets this object to valid(1) or aborts, setting this
         object to invalid(4).  If the agent determines that an
         entry has been in the underCreation(3) state for an
         abnormally long time, it may decide that the management
         station has crashed.  If the agent makes this decision,
         it may set this object to invalid(4) to reclaim the
         entry.  A prudent agent will understand that the
         management station may need to wait for human input
         and will allow for that possibility in its
         determination of this abnormally long period.

         An entry in the valid(1) state is fully configured and
         consistent and fully represents the configuration or
         operation such a row is intended to represent.  For
         example, it could be a statistical function that is
         configured and active, or a filter that is available
         in the list of filters processed by the packet capture
         process.

         A manager is restricted to changing the state of an entry in
         the following ways:

              To:       valid  createRequest  underCreation  invalid
         From:
         valid             OK             NO             OK       OK
         createRequest    N/A            N/A            N/A      N/A
         underCreation     OK             NO             OK       OK
         invalid           NO             NO             NO       OK
         nonExistent       NO             OK             NO       OK

         In the table above, it is not applicable to move the state
         from the createRequest state to any other state because the
         manager will never find the variable in that state.  The
         nonExistent state is not a value of the enumeration, rather
         it means that the entryStatus variable does not exist at all.

         An agent may allow an entryStatus variable to change state in
         additional ways, so long as the semantics of the states are
         followed.  This allowance is made to ease the implementation of
         the agent and is made despite the fact that managers should
         never exercise these additional state transitions."
	SYNTAX INTEGER {
                valid(1),
                createRequest(2),
                underCreation(3),
                invalid(4)
            }  
			
PortLaMode ::= TEXTUAL-CONVENTION
	STATUS         current
	DESCRIPTION    
			"Defines how a Port Channel does channeling.
			lacp(1)      - place the port into passive 
							   negotiation state, in which the
							   port waits for its peer to 
							   initiate negotiation.
			manual(2)    - force the port to enable 
							   channeling.
			disable(3)   - channeling is disabled."                     
	SYNTAX INTEGER {
					lacp(1),
					manual(2),
					disable(3)
			}
			
AuthenticMethod ::= TEXTUAL-CONVENTION 
	STATUS      current 
	DESCRIPTION 
			"The Authentication method is using Remote Authentication 
			Server or Local Authentication Server." 
	SYNTAX INTEGER { 
					remoteServer(1), 
					localServer(2) 
			} 

PaeControlledDirections ::= TEXTUAL-CONVENTION 
	STATUS      current 
	DESCRIPTION 
			"The control mode values for the Authenticator PAE." 
	SYNTAX	INTEGER { 
					both(0), 
					in(1) 
			} 

PaeControlledPortStatus ::= TEXTUAL-CONVENTION 
	STATUS       current 
	DESCRIPTION 
			"The status values of the Authenticator PAE controlled 
			Port." 
	SYNTAX	INTEGER { 
					authorized(1), 
					unauthorized(2) 
			}


PaeControlledPortControl ::= TEXTUAL-CONVENTION 
	STATUS       current 
	DESCRIPTION 
			"The control values of the Authenticator PAE controlled 
			Port." 
	SYNTAX	INTEGER { 
					forceUnauthorized(1), 
					auto(2), 
					forceAuthorized(3) 
			} 


PermissionType ::= TEXTUAL-CONVENTION 
	STATUS      current 
	DESCRIPTION 
			"The permission values." 
	SYNTAX	INTEGER { 
					allow(1), 
					deny(2) 
			}
 
ZeroBasedCounter32 ::= TEXTUAL-CONVENTION
    STATUS current
    DESCRIPTION
        "This TC describes an object that counts events with the
        following semantics: objects of this type will be set to
        zero(0) on creation and will thereafter count appropriate
        events, wrapping back to zero(0) when the value 2^32 is
        reached.

        Provided that an application discovers the new object within
        the minimum time to wrap, it can use the initial value as a
        delta since it last polled the table of which this object is
        part.  It is important for a management station to be aware of
        this minimum time and the actual time between polls, and to
        discard data if the actual time is too long or there is no
        defined minimum time.

        Typically, this TC is used in tables where the INDEX space is
        constantly changing and/or the TimeFilter mechanism is in use."
    SYNTAX Gauge32

LastCreateTime ::= TEXTUAL-CONVENTION
    STATUS current
    DESCRIPTION
        "This TC describes an object that stores the value of the
        sysUpTime object at the last time its entry was created.

        This can be used for polling applications to determine that an
        entry has been deleted and re-created between polls, causing
        an otherwise undetectable discontinuity in the data.

        If sysUpTime is reset to zero as a result of a re-
        initialization of the network management (sub)system, then
        the values of all LastCreateTime objects are also reset.
        However, after approximately 497 days without a re-
        initialization, the sysUpTime object will reach 2^^32-1 and
        then increment to zero; in this case, existing values
        of TimeStamp objects do not change.  This can lead to
        ambiguities in the value of TimeStamp objects."
    SYNTAX TimeTicks

TimeFilter ::= TEXTUAL-CONVENTION
  STATUS        current
  DESCRIPTION
      "To be used for the index to a table.  Allows an application
      to download only those rows changed since a particular time.
      Note that this is not a history mechanism.  Only current values
      of underlying objects are returned; saved instance values
      associated with particular values of sysUpTime are not.

      An entry is considered changed if the value of any object in the
      entry changes, if the row is created, or if any object in the
      entry is created or deleted.  Note that deleted entries cannot
      be detected or downloaded.

      A time-filtered conceptual table is created by inserting a
      single object of SYNTAX TimeFilter as the first INDEX component
      in a copy of an existing basic conceptual table (i.e., any
      SEQUENCE without a TimeFilter INDEX component).  Thus, for
      each conceptual entry 'I' in the basic table, there exists N
      conceptual entries in the time-filtered version, indexed N.I,
      where 'N' is equal to the value of sysUpTime.

      When an application retrieves conceptual instances from a
      time-filtered table, and an INDEX value is provided for the
      TimeFilter INDEX component 'N', the agent will only consider
      returning basic conceptual entries (e.g., 'fooColumn.N.I') if
      any column within the basic conceptual entry has changed since
      sysUpTime 'N'.  If not, the basic conceptual entry will
      be ignored for the particular retrieval operation.

      When sysUpTime is equal to zero, this table shall be empty.

      One conceptual entry exists for each past value of sysUpTime,
      except that the whole table is purged should sysUpTime wrap.

      As an entry in a time-filtered table is updated (i.e., one of
      the columns in the basic conceptual table is changed), new
      conceptual entries are also created in the time-filtered version
      (which still shares the now updated object values with all other
      instances).  The number of unique time-filtered instances that
      are created is determined by the value of sysUpTime at which the
      basic entry was last updated.  One unique instance will exist
      for each value of sysUpTime at the last update time for the row.
      However, a new TimeFilter index instance is created for each new
      sysUpTime value.  The TimeFilter index values not associated
      with entry updates are called duplicate time-filtered instances.

      After some deployment experience, it has been determined that
      a time-filtered table is more efficient if the agent
      stops a MIB walk operation by skipping over rows with a
      TimeFilter index value higher than the value in the received
      GetNext/GetBulk request.  That is, instead of incrementing a
      TimeFilter index value, the agent will continue to the next
      object or table.  As a consequence, GetNext or GetBulk
      operations will provide only one pass through a time-filtered
      table.

      It is suggested that an agent implement a time-filtered table
      in this manner to improve performance and avoid a MIB walk
      getting stuck in time-filtered tables.  It is, however, still
      acceptable for an agent to implement a time-filtered table in
      the traditional manner (i.e., every conceptual time-filtered
      instance is returned in GetNext and GetBulk PDU responses), and
      management applications must be able to deal with such
      traditional implementations.

      See the appendix for further discussion of this textual
      convention.

      The following example is provided to demonstrate TimeFilter
      behavior:

      Consider the following basic conceptual table, basicFooTable.
      (Note that the basic version of a time-filtered table may not
      actually be defined.)

          basicFooTable:

          basicFooTable ...
          INDEX { fooIndex }

          BasicFooEntry {
             fooIndex     Integer32,
             fooCounts    Counter32
          }

      For this example, the basicFooTable contains two static
      conceptual entries (fooIndex equals '1' and '2'), created at
      time zero.  It also contains one dynamic conceptual entry
      (fooIndex equals '3'), which is created at time '3' and deleted
      at time '7'.

      The time-filtered version of the basicFooTable could be defined
      as follows:

          FooTable:

          fooTable ...
          INDEX { fooTimeMark, fooIndex }

          FooEntry {
             fooTimeMark  TimeFilter,
             fooIndex     Integer32,
             fooCounts    Counter32
          }


      Note that entries exist in the time-filtered conceptual table
      only if they actually exist in the underlying (basic) table.

      For this example, the fooTable will have three underlying
      basic entries (fooIndex == 1, 2, and 3), with the following
      activity (for sysUpTime equal 0 to 9):

         - fooEntry.N.1 is created at time '0' and most recently
           updated at time '6' to the value '5'.
         - fooEntry.N.2 is created at time '0' and most recently
           updated at time '8' to the value '9'.
         - fooEntry.N.3 is created at time '3', updated at time '5'
           to the value '17', and deleted at time '7'.

     The following tables show the values that would be returned for
     MIB walk operations with various TimeFilter values, done at
     different times.  An application issues a retrieval request at
     time 'T', with a TimeFilter value, 'N' (typically set to a lower
     value, such as the value of sysUpTime at the last polling cycle).

     The following values would be returned in a MIB walk of
     fooCounts.N if T equals '0' and N equals '0':

           fooCounts.N.I    Value
           ==========================
           fooCounts.0.1    0
           fooCounts.0.2    0

       Note that nothing is returned for fooCounts.0.3, since that
       entry does not exist at sysUpTime equals '0'.

     The following values would be returned in a full (traditional) MIB
     walk of fooCounts.N if T equals '3' and N equals '0':

           fooCounts.N.I    Value
           =======================
           fooCounts.0.1    0
           fooCounts.0.2    0
           fooCounts.0.3    0
           fooCounts.1.3    0
           fooCounts.2.3    0
           fooCounts.3.3    0

       Note that there are no instances for T equals 1 or 2 for the
       first two values of N, as these entries did not change
       since they were created at time '0'.

       Note that the current value for 'fooCounts.N.3' is returned
       here, even for values of N less than '3' (when the entry was
       created).  The agent only considers the current existence of an
       entry in the TimeFilter algorithm, not the time when the entry
       was created.

       Note that the instances 'fooCounts.0.3', 'fooCounts.1.3',
       and 'fooCounts.2.3' are duplicates and can be suppressed by the
       agent in a MIB walk.

     The following values would be returned in a full (traditional)
     MIB walk of fooCounts.N if T equals '6' and N equals '3':

           fooCounts.N.I    Value
           =======================
           fooCounts.3.1    5
           fooCounts.3.3    17
           fooCounts.4.1    5
           fooCounts.4.3    17
           fooCounts.5.1    5
           fooCounts.5.3    17
           fooCounts.6.1    5

        Note that no instances for entry 'fooCounts.N.2' are returned,
        since it has not changed since time '3'.

        Note that all instances except 'fooCounts.5.3' and
        'fooCounts.6.1' are duplicates and can be suppressed by the
        agent in a MIB walk.

     The following values would be returned in a full (traditional)
     MIB walk of fooCounts.N if T equals '9' and N equals '6':

           fooCounts.N.I    Value
           =======================
           fooCounts.6.1    5
           fooCounts.6.2    9
           fooCounts.7.2    9
           fooCounts.8.2    9

        Note that no instances for entry 'fooCounts.N.3' are returned,
        since it was deleted at time '7'.

        Note that instances 'fooCounts.6.2' and 'fooCounts.7.2'
        are duplicates and can be suppressed by the agent in a MIB
        walk."

  SYNTAX    TimeTicks

DataSource ::= TEXTUAL-CONVENTION
    STATUS        current
    DESCRIPTION
        "Identifies the source of the data that the associated
        function is configured to analyze.  This source can be any
        interface on this device.

        In order to identify a particular interface, this
        object shall identify the instance of the ifIndex
        object, defined in [RFC 2863], for the desired interface.

        For example, if an entry were to receive data from
        interface #1, this object would be set to ifIndex.1."
    SYNTAX      OBJECT IDENTIFIER 

      CusSFlowDataSource ::= TEXTUAL-CONVENTION
              STATUS      current
              DESCRIPTION
                "Identifies a source of sFlow data.

                The following data source types are currently defined:

                - ifIndex.<I>
                SFlowDataSources of this traditional form are called
                'port-based'. Ideally the sampling entity will perform 
                sampling on all flows originating from or destined to 
                the specified interface. However, if the switch architecture 
                only allows input or output sampling then the sampling agent 
                is permitted to only sample input flows input or output flows. 
                Each packet must only be considered once for sampling, 
                irrespective of the number of ports it will be forwarded to.
                Note: Port 0 is used to indicate that all ports on the device
                      are represented by a single data source.
                      - sFlowFsPacketSamplingRate applies to all ports on the
                        device capable of packet sampling.

                - smonVlanDataSource.<V>
                An SFlowDataSource of this form refers to a 'Packet-based VLAN'
                and is called a 'VLAN-based' dataSource. <V> is the VLAN
                ID as defined by the IEEE 802.1Q standard. The
                value is between 1 and 4094 inclusive, and it represents
                an 802.1Q VLAN-ID with global scope within a given
                bridged domain.
                Sampling is performed on all packets received that are part
                of the specified VLAN (no matter which port they arrived on).
                Each packet will only be considered once for sampling,
                irrespective of the number of ports it will be forwarded to.
                
                - entPhysicalEntry.<N>
                An SFlowDataSource of this form refers to a physical entity 
                within the agent (e.g. entPhysicalClass = backplane(4)) and 
                is called an 'entity-based' dataSource. Sampling is performed 
                on all packets entering the resource (e.g. If the backplane 
                is being sampled, all packets transmitted onto the backplane 
                will be considered as single candidates for sampling 
                irrespective of the number of ports they ultimately reach).

                Note: Since each SFlowDataSource operates independently a 
                      packet that crosses multiple DataSources may generate 
                      multiple flow records."
              SYNTAX      OBJECT IDENTIFIER

      CusSFlowInstance ::= TEXTUAL-CONVENTION
              STATUS      current
              DESCRIPTION
                "If more than one sFlow sampler is available for this
                 SFlowDataSource then individual samplers are distinguished
                 using the SFlowInstance variable. The value of 
                 SFlowInstance ranges from 1..n where n is the number of
                 samplers associated with this SFlowDataSource.

                 Note: Each sFlow sampler instance must operate
                       independently of all other instances. Setting
                       an attribute of one sampler must not alter the
                       the behavior and settings of other sampler
                       instances."
              SYNTAX      Integer32 (1..65535)

      CusSFlowReceiver ::= TEXTUAL-CONVENTION
              STATUS       current
              DESCRIPTION
                "Identify the sFlow receiver associated with this resource.

                 A value of zero indicates that this resource is available.
                 If non-zero the value must correspond to a valid, active 
                 sFlowRcvrIndex.

                 If the value is currently zero it may be set to any
                 active entry in the sFlowRcvrTable. If the value is
                 not zero then a set to anything other than zero or
                 its current value will result in an SNMP error (bad value).

                 Setting to zero frees the resource and returns all the
                 values in this entry to their default values.

                 If an entry in the sFlowRcvrTable expires, either
                 because the sFlowRcvrOwner is set to the empty
                 string or because the sFlowRcvrTimeout reaches zero, then
                 the agent must mark all associated resources as available
                 (by setting the associated SFlowReceiver entry to zero)
                 and all values in these records must be restored to their
                 default values.

                 This mechanism provides no enforcement and relies on the
                 cooperation of management entities in order to ensure that
                 competition for a resource is fairly resolved. A management
                 entity should not make any changes to a resource
                 without first aquiring it by successfully writing its
                 sFlowRcvrIndex value as the SFlowReceiver for the resource."
              SYNTAX       Integer32
			  
			  
			  
			  
			  
			    LldpChassisIdSubtype ::= TEXTUAL-CONVENTION
    STATUS      current
    DESCRIPTION
            "This TC describes the source of a chassis identifier.

            The enumeration 'chassisComponent(1)' represents a chassis
            identifier based on the value of entPhysicalAlias object
            (defined in IETF RFC 2737) for a chassis component (i.e.,
            an entPhysicalClass value of 'chassis(3)').

            The enumeration 'interfaceAlias(2)' represents a chassis
            identifier based on the value of ifAlias object (defined in
            IETF RFC 2863) for an interface on the containing chassis.

            The enumeration 'portComponent(3)' represents a chassis
            identifier based on the value of entPhysicalAlias object
            (defined in IETF RFC 2737) for a port or backplane
            component (i.e., entPhysicalClass value of 'port(10)' or
            'backplane(4)'), within the containing chassis.

            The enumeration 'macAddress(4)' represents a chassis
            identifier based on the value of a unicast source address
            (encoded in network byte order and IEEE 802.3 canonical bit
            order), of a port on the containing chassis as defined in
            IEEE Std 802-2001.

            The enumeration 'networkAddress(5)' represents a chassis
            identifier based on a network address, associated with
            a particular chassis.  The encoded address is actually
            composed of two fields.  The first field is a single octet,
            representing the IANA AddressFamilyNumbers value for the
            specific address type, and the second field is the network
            address value.

            The enumeration 'interfaceName(6)' represents a chassis
            identifier based on the value of ifName object (defined in
            IETF RFC 2863) for an interface on the containing chassis.

            The enumeration 'local(7)' represents a chassis identifier
            based on a locally defined value."
    SYNTAX  INTEGER {
            chassisComponent(1),
            interfaceAlias(2),
            portComponent(3),
            macAddress(4),
            networkAddress(5),
            interfaceName(6),
            local(7)
    }

LldpChassisId ::= TEXTUAL-CONVENTION
    STATUS      current
    DESCRIPTION
            "This TC describes the format of a chassis identifier string.
            Objects of this type are always used with an associated
            LldpChassisIdSubtype object, which identifies the format of
            the particular LldpChassisId object instance.

            If the associated LldpChassisIdSubtype object has a value of
            'chassisComponent(1)', then the octet string identifies
            a particular instance of the entPhysicalAlias object
            (defined in IETF RFC 2737) for a chassis component (i.e.,
            an entPhysicalClass value of 'chassis(3)').

            If the associated LldpChassisIdSubtype object has a value
            of 'interfaceAlias(2)', then the octet string identifies
            a particular instance of the ifAlias object (defined in
            IETF RFC 2863) for an interface on the containing chassis.
            If the particular ifAlias object does not contain any values,
            another chassis identifier type should be used.

            If the associated LldpChassisIdSubtype object has a value
            of 'portComponent(3)', then the octet string identifies a
            particular instance of the entPhysicalAlias object (defined
            in IETF RFC 2737) for a port or backplane component within
            the containing chassis.

            If the associated LldpChassisIdSubtype object has a value of
            'macAddress(4)', then this string identifies a particular
            unicast source address (encoded in network byte order and
            IEEE 802.3 canonical bit order), of a port on the containing
            chassis as defined in IEEE Std 802-2001.

            If the associated LldpChassisIdSubtype object has a value of
            'networkAddress(5)', then this string identifies a particular
            network address, encoded in network byte order, associated
            with one or more ports on the containing chassis.  The first
            octet contains the IANA Address Family Numbers enumeration
            value for the specific address type, and octets 2 through
            N contain the network address value in network byte order.

            If the associated LldpChassisIdSubtype object has a value
            of 'interfaceName(6)', then the octet string identifies
            a particular instance of the ifName object (defined in
            IETF RFC 2863) for an interface on the containing chassis.
            If the particular ifName object does not contain any values,
            another chassis identifier type should be used.

            If the associated LldpChassisIdSubtype object has a value of
            'local(7)', then this string identifies a locally assigned
            Chassis ID."
    SYNTAX      OCTET STRING (SIZE (1..255))

LldpPortIdSubtype ::= TEXTUAL-CONVENTION
    STATUS      current
    DESCRIPTION
            "This TC describes the source of a particular type of port
            identifier used in the LLDP MIB.

            The enumeration 'interfaceAlias(1)' represents a port
            identifier based on the ifAlias MIB object, defined in IETF
            RFC 2863.

            The enumeration 'portComponent(2)' represents a port
            identifier based on the value of entPhysicalAlias (defined in
            IETF RFC 2737) for a port component (i.e., entPhysicalClass
            value of 'port(10)'), within the containing chassis.

            The enumeration 'macAddress(3)' represents a port identifier
            based on a unicast source address (encoded in network
            byte order and IEEE 802.3 canonical bit order), which has
            been detected by the agent and associated with a particular
            port (IEEE Std 802-2001).

            The enumeration 'networkAddress(4)' represents a port
            identifier based on a network address, detected by the agent
            and associated with a particular port.

            The enumeration 'interfaceName(5)' represents a port
            identifier based on the ifName MIB object, defined in IETF
            RFC 2863.

            The enumeration 'agentCircuitId(6)' represents a port
            identifier based on the agent-local identifier of the circuit
            (defined in RFC 3046), detected by the agent and associated
            with a particular port.

            The enumeration 'local(7)' represents a port identifier
            based on a value locally assigned."

    SYNTAX  INTEGER {
            interfaceAlias(1),
            portComponent(2),
            macAddress(3),
            networkAddress(4),
            interfaceName(5),
            agentCircuitId(6),
            local(7)
    }

LldpPortId ::= TEXTUAL-CONVENTION
    STATUS      current
    DESCRIPTION
            "This TC describes the format of a port identifier string.
            Objects of this type are always used with an associated
            LldpPortIdSubtype object, which identifies the format of the
            particular LldpPortId object instance.

            If the associated LldpPortIdSubtype object has a value of
            'interfaceAlias(1)', then the octet string identifies a
            particular instance of the ifAlias object (defined in IETF
            RFC 2863).  If the particular ifAlias object does not contain
            any values, another port identifier type should be used.

            If the associated LldpPortIdSubtype object has a value of
            'portComponent(2)', then the octet string identifies a
            particular instance of the entPhysicalAlias object (defined
            in IETF RFC 2737) for a port or backplane component.

            If the associated LldpPortIdSubtype object has a value of
            'macAddress(3)', then this string identifies a particular
            unicast source address (encoded in network byte order
            and IEEE 802.3 canonical bit order) associated with the port
            (IEEE Std 802-2001).

            If the associated LldpPortIdSubtype object has a value of
            'networkAddress(4)', then this string identifies a network
            address associated with the port.  The first octet contains
            the IANA AddressFamilyNumbers enumeration value for the
            specific address type, and octets 2 through N contain the
            networkAddress address value in network byte order.

            If the associated LldpPortIdSubtype object has a value of
            'interfaceName(5)', then the octet string identifies a
            particular instance of the ifName object (defined in IETF
            RFC 2863).  If the particular ifName object does not contain
            any values, another port identifier type should be used.

            If the associated LldpPortIdSubtype object has a value of
            'agentCircuitId(6)', then this string identifies a agent-local
            identifier of the circuit (defined in RFC 3046).

            If the associated LldpPortIdSubtype object has a value of
            'local(7)', then this string identifies a locally
            assigned port ID."
    SYNTAX      OCTET STRING (SIZE (1..255))

LldpManAddrIfSubtype ::= TEXTUAL-CONVENTION
    STATUS      current
    DESCRIPTION
            "This TC describes the basis of a particular type of
            interface associated with the management address.

            The enumeration 'unknown(1)' represents the case where the
            interface is not known.

            The enumeration 'ifIndex(2)' represents interface identifier
            based on the ifIndex MIB object.

            The enumeration 'systemPortNumber(3)' represents interface
            identifier based on the system port numbering convention."
    REFERENCE 
            "IEEE 802.1AB-2005 9.5.9.5"
            
    SYNTAX  INTEGER {
            unknown(1),
            ifIndex(2),
            systemPortNumber(3)
    }

LldpManAddress ::= TEXTUAL-CONVENTION
    STATUS      current
    DESCRIPTION
            "The value of a management address associated with the LLDP
            agent that may be used to reach higher layer entities to
            assist discovery by network management.

            It should be noted that appropriate security credentials,
            such as SNMP engineId, may be required to access the LLDP
            agent using a management address.  These necessary credentials
            should be known by the network management and the objects
            associated with the credentials are not included in the
            LLDP agent."
    SYNTAX      OCTET STRING (SIZE (1..31))

LldpSystemCapabilitiesMap ::= TEXTUAL-CONVENTION
    STATUS      current
    DESCRIPTION
            "This TC describes the system capabilities.

            The bit 'other(0)' indicates that the system has capabilities
            other than those listed below.

            The bit 'repeater(1)' indicates that the system has repeater
            capability.

            The bit 'bridge(2)' indicates that the system has bridge
            capability.

            The bit 'wlanAccessPoint(3)' indicates that the system has 
            WLAN access point capability.

            The bit 'router(4)' indicates that the system has router
            capability.

            The bit 'telephone(5)' indicates that the system has telephone
            capability.

            The bit 'docsisCableDevice(6)' indicates that the system has
            DOCSIS Cable Device capability (IETF RFC 2669 & 2670).

            The bit 'stationOnly(7)' indicates that the system has only
            station capability and nothing else."
    SYNTAX  BITS {
            other(0),
            repeater(1),
            bridge(2),
            wlanAccessPoint(3),
            router(4),
            telephone(5),
            docsisCableDevice(6),
            stationOnly(7)
    }

LldpPortNumber ::= TEXTUAL-CONVENTION
    DISPLAY-HINT "d"
    STATUS     current 
    DESCRIPTION
            "Each port contained in the chassis (that is known to the
            LLDP agent) is uniquely identified by a port number.

            A port number has no mandatory relationship to an
            InterfaceIndex object (of the interfaces MIB, IETF RFC 2863).
            If the LLDP agent is a IEEE 802.1D, IEEE 802.1Q bridge, the
            LldpPortNumber will have the same value as the dot1dBasePort
            object (defined in IETF RFC 1493) associated corresponding
            bridge port.  If the system hosting LLDP agent is not an
            IEEE 802.1D or an IEEE 802.1Q bridge, the LldpPortNumber
            will have the same value as the corresponding interface's
            InterfaceIndex object.

            Port numbers should be in the range of 1 and 4096 since a
            particular port is also represented by the corresponding
            port number bit in LldpPortList."
    SYNTAX 	Integer32(1..4096)

LldpPortList ::= TEXTUAL-CONVENTION
    STATUS      current
    DESCRIPTION
            "Each octet within this value specifies a set of eight ports,
            with the first octet specifying ports 1 through 8, the second
            octet specifying ports 9 through 16, etc.  Within each octet,
            the most significant bit represents the lowest numbered port,
            and the least significant bit represents the highest numbered
            port.  Thus, each port of the system is represented by a
            single bit within the value of this object.  If that bit has
            a value of '1' then that port is included in the set of ports;
            the port is not included if its bit has a value of '0'."
    REFERENCE 
            "IETF RFC 2674 section 5"
    SYNTAX  OCTET STRING(SIZE(0..512))
    
LldpPowerPortClass ::= TEXTUAL-CONVENTION
    STATUS      current
    DESCRIPTION
            "This TC describes the Power over Ethernet (PoE) port class."
    SYNTAX  INTEGER {
            pClassPSE(1),
            pClassPD(2)
    }

LldpLinkAggStatusMap ::= TEXTUAL-CONVENTION
    STATUS      current
    DESCRIPTION
            "This TC describes the link aggregation status.

            The bit 'aggCapable(0)' indicates the link is capable of being
            aggregated. 

            The bit 'aggEnabled(1)' indicates the link is currently in
            aggregation."
    SYNTAX  BITS {
            aggCapable(0),
            aggEnabled(1)
    }
 -- LLDP-MED Capabilities TC

LldpXMedCapabilities ::= TEXTUAL-CONVENTION
 	STATUS  current
 	DESCRIPTION
           "Bitmap that includes the MED organizationally defined set of LLDP
            TLVs the device is capable of and whose transmission is allowed on
            the local LLDP agent by network management.

            Each bit in the bitmap corresponds to an LLDP-MED subtype associated
            with a specific TIA TR41.4 MED TLV.

            Having the bit 'capabilities(0)' set indicates that the LLDP
            agent refers to the Capabilities TLVs.

            Having the bit 'networkPolicy(1)' set indicates that the LLDP
            agent refers to the Network Policy TLVs.

            Having the bit 'location(2)' set indicates that
            the LLDP agent refers to the Emergency Communications
            System Location TLVs.

            Having the bit 'extendedPSE(3)' set indicates that
            the LLDP agent refers to the Extended PoE TLVs with PSE
            capabilities.

            Having the bit 'extendedPD(4)' set indicates that
            the LLDP agent refers to the Extended PoE TLVs with PD
            capabilities.

            Having the bit 'inventory(5)' set indicates that
            the LLDP agent refers to the Hardware Revision, Firmware
            Revision, Software Revision, Serial Number, Manufacturer Name,
            Model Name, and Asset ID TLVs."

    SYNTAX  BITS  {
            capabilities(0),
            networkPolicy(1),
            location(2),
            extendedPSE(3),
            extendedPD(4),
            inventory(5)
     	}

 PolicyAppType ::= TEXTUAL-CONVENTION
    STATUS      current
    DESCRIPTION
            "The media type that defines the primary function of the
             application for the policy advertised by an endpoint.

             Having the bit voice(1) set indicates that the media type defining
             a primary function of the application for the policy advertised on
             the local port is voice.

             Having the bit voiceSignaling(3) set indicates that the media type
             defining a primary function of the application for the policy
             advertised on the local port is voice signaling.

             Having the bit guestVoice(4) set indicates that the media type
             Defining a primary function of the application for the policy
             advertised on the local port is guest voice.

             Having the bit guestVoiceSignaling(5) set indicates that the media
             type defining a primary function of the application for the policy
             advertised on the local port is guest voice signaling.

             Having the bit softPhoneVoice(6) set indicates that the media type
             Defining a primary function of the application for the policy
             advertised on the local port is softphone voice.

             Having the bit videoConferencing(7) set indicates that the media
             type defining a primary function of the application for the policy
             advertised on the local port is voice.

             Having the bit streamingVideo(8) set indicates that the media type
             defining a primary function of the application for the policy
             advertised on  the local port is streaming video.

             Having the bit videoSignaling(2) set indicates that the media type
             defining a primary function of the application for the policy
             advertised on the local port is video signaling."
    SYNTAX      BITS  {
                    unknown(0),
                    voice(1),
                    voiceSignaling(2),
                    guestVoice(3),
                    guestVoiceSignaling(4),
                    softPhoneVoice(5),
                    videoconferencing(6),
                    streamingVideo(7),
                    videoSignaling(8)
                }


	
AddressFamilyNumbers ::= TEXTUAL-CONVENTION

      STATUS       current
      DESCRIPTION
          "The definition of this textual convention with the
          addition of newly assigned values is published
          periodically by the IANA, in either the Assigned
          Numbers RFC, or some derivative of it specific to
          Internet Network Management number assignments.
          (The latest arrangements can be obtained by
          contacting the IANA.)

          The enumerations are described as:

          other(0),    -- none of the following
          ipV4(1),     -- IP Version 4
          ipV6(2),     -- IP Version 6
          nsap(3),     -- NSAP
          hdlc(4),     -- (8-bit multidrop)
          bbn1822(5),
          all802(6),   -- (includes all 802 media
                       --   plus Ethernet 'canonical format')
          e163(7),
          e164(8),     -- (SMDS, Frame Relay, ATM)
          f69(9),      -- (Telex)
          x121(10),    -- (X.25, Frame Relay)
          ipx(11),     -- IPX (Internet Protocol Exchange)
          appleTalk(12),  -- Apple Talk
          decnetIV(13),   -- DEC Net Phase IV
          banyanVines(14),  -- Banyan Vines
          e164withNsap(15),
                       -- (E.164 with NSAP format subaddress)
          dns(16),     -- (Domain Name System)
          distinguishedName(17), -- (Distinguished Name, per X.500)
          asNumber(18), -- (16-bit quantity, per the AS number space)
          xtpOverIpv4(19),  -- XTP over IP version 4
          xtpOverIpv6(20),  -- XTP over IP version 6
          xtpNativeModeXTP(21),  -- XTP native mode XTP
          fibreChannelWWPN(22),  -- Fibre Channel World-Wide Port Name 
          fibreChannelWWNN(23),  -- Fibre Channel World-Wide Node Name
          gwid(24),    -- Gateway Identifier 
          afi(25),  -- AFI for L2VPN information
          reserved(65535)



          Requests for new values should be made to IANA via
          email (iana&iana.org)."

      SYNTAX  INTEGER {
                  other(0),
                  ipV4(1),
                  ipV6(2),
                  nsap(3),
                  hdlc(4),
                  bbn1822(5),
                  all802(6),
                  e163(7),
                  e164(8),
                  f69(9),
                  x121(10),
                  ipx(11),
                  appleTalk(12),
                  decnetIV(13),
                  banyanVines(14),
                  e164withNsap(15),
                  dns(16),
                  distinguishedName(17), -- (Distinguished Name, per X.500)
                  asNumber(18), -- (16-bit quantity, per the AS number space)
                  xtpOverIpv4(19),
                  xtpOverIpv6(20),
                  xtpNativeModeXTP(21),
                  fibreChannelWWPN(22),
                  fibreChannelWWNN(23),
                  gwid(24),
                  afi(25),
                  reserved(65535)
              }


   IANAifType ::= TEXTUAL-CONVENTION
       STATUS       current
       DESCRIPTION
               "This data type is used as the syntax of the ifType
               object in the (updated) definition of MIB-II's
               ifTable.

               The definition of this textual convention with the
               addition of newly assigned values is published
               periodically by the IANA, in either the Assigned
               Numbers RFC, or some derivative of it specific to
               Internet Network Management number assignments.  (The
               latest arrangements can be obtained by contacting the
               IANA.)

               Requests for new values should be made to IANA via
               email (iana&iana.org).

               The relationship between the assignment of ifType
               values and of OIDs to particular media-specific MIBs
               is solely the purview of IANA and is subject to change
               without notice.  Quite often, a media-specific MIB's
               OID-subtree assignment within MIB-II's 'transmission'
               subtree will be the same as its ifType value.
               However, in some circumstances this will not be the
               case, and implementors must not pre-assume any
               specific relationship between ifType values and
               transmission subtree OIDs."
       SYNTAX  INTEGER {
                   other(1),          -- none of the following
                   regular1822(2),
                   hdh1822(3),
                   ddnX25(4),
                   rfc877x25(5),
                   ethernetCsmacd(6), -- for all ethernet-like interfaces,
                                      -- regardless of speed, as per RFC3635
                   iso88023Csmacd(7), -- Deprecated via RFC3635
                                      -- ethernetCsmacd (6) should be used instead
                   iso88024TokenBus(8),
                   iso88025TokenRing(9),
                   iso88026Man(10),
                   starLan(11), -- Deprecated via RFC3635
                                -- ethernetCsmacd (6) should be used instead
                   proteon10Mbit(12),
                   proteon80Mbit(13),
                   hyperchannel(14),
                   fddi(15),
                   lapb(16),
                   sdlc(17),
                   ds1(18),            -- DS1-MIB
                   e1(19),             -- Obsolete see DS1-MIB
                   basicISDN(20),              -- no longer used
                                               -- see also RFC2127
                   primaryISDN(21),            -- no longer used
                                               -- see also RFC2127
                   propPointToPointSerial(22), -- proprietary serial
                   ppp(23),
                   softwareLoopback(24),
                   eon(25),            -- CLNP over IP 
                   ethernet3Mbit(26),
                   nsip(27),           -- XNS over IP
                   slip(28),           -- generic SLIP
                   ultra(29),          -- ULTRA technologies
                   ds3(30),            -- DS3-MIB
                   sip(31),            -- SMDS, coffee
                   frameRelay(32),     -- DTE only. 
                   rs232(33),
                   para(34),           -- parallel-port
                   arcnet(35),         -- arcnet
                   arcnetPlus(36),     -- arcnet plus
                   atm(37),            -- ATM cells
                   miox25(38),
                   sonet(39),          -- SONET or SDH 
                   x25ple(40),
                   iso88022llc(41),
                   localTalk(42),
                   smdsDxi(43),
                   frameRelayService(44),  -- FRNETSERV-MIB
                   v35(45),
                   hssi(46),
                   hippi(47),
                   modem(48),          -- Generic modem
                   aal5(49),           -- AAL5 over ATM
                   sonetPath(50),
                   sonetVT(51),
                   smdsIcip(52),       -- SMDS InterCarrier Interface
                   propVirtual(53),    -- proprietary virtual/internal
                   propMultiplexor(54),-- proprietary multiplexing
                   ieee80212(55),      -- 100BaseVG
                   fibreChannel(56),   -- Fibre Channel
                   hippiInterface(57), -- HIPPI interfaces     
                   frameRelayInterconnect(58), -- Obsolete use either
                                       -- frameRelay(32) or 
                                       -- frameRelayService(44).
                   aflane8023(59),     -- ATM Emulated LAN for 802.3
                   aflane8025(60),     -- ATM Emulated LAN for 802.5
                   cctEmul(61),        -- ATM Emulated circuit          
                   fastEther(62),      -- Obsoleted via RFC3635
                                       -- ethernetCsmacd (6) should be used instead
                   isdn(63),           -- ISDN and X.25           
                   v11(64),            -- CCITT V.11/X.21             
                   v36(65),            -- CCITT V.36                  
                   g703at64k(66),      -- CCITT G703 at 64Kbps
                   g703at2mb(67),      -- Obsolete see DS1-MIB
                   qllc(68),           -- SNA QLLC                    
                   fastEtherFX(69),    -- Obsoleted via RFC3635
                                       -- ethernetCsmacd (6) should be used instead
                   channel(70),        -- channel                     
                   ieee80211(71),      -- radio spread spectrum       
                   ibm370parChan(72),  -- IBM System 360/370 OEMI Channel
                   escon(73),          -- IBM Enterprise Systems Connection
                   dlsw(74),           -- Data Link Switching
                   isdns(75),          -- ISDN S/T interface
                   isdnu(76),          -- ISDN U interface
                   lapd(77),           -- Link Access Protocol D
                   ipSwitch(78),       -- IP Switching Objects
                   rsrb(79),           -- Remote Source Route Bridging
                   atmLogical(80),     -- ATM Logical Port
                   ds0(81),            -- Digital Signal Level 0
                   ds0Bundle(82),      -- group of ds0s on the same ds1
                   bsc(83),            -- Bisynchronous Protocol
                   async(84),          -- Asynchronous Protocol
                   cnr(85),            -- Combat Net Radio
                   iso88025Dtr(86),    -- ISO 802.5r DTR
                   eplrs(87),          -- Ext Pos Loc Report Sys
                   arap(88),           -- Appletalk Remote Access Protocol
                   propCnls(89),       -- Proprietary Connectionless Protocol
                   hostPad(90),        -- CCITT-ITU X.29 PAD Protocol
                   termPad(91),        -- CCITT-ITU X.3 PAD Facility
                   frameRelayMPI(92),  -- Multiproto Interconnect over FR
                   x213(93),           -- CCITT-ITU X213
                   adsl(94),           -- Asymmetric Digital Subscriber Loop
                   radsl(95),          -- Rate-Adapt. Digital Subscriber Loop
                   sdsl(96),           -- Symmetric Digital Subscriber Loop
                   vdsl(97),           -- Very H-Speed Digital Subscrib. Loop
                   iso88025CRFPInt(98), -- ISO 802.5 CRFP
                   myrinet(99),        -- Myricom Myrinet
                   voiceEM(100),       -- voice recEive and transMit
                   voiceFXO(101),      -- voice Foreign Exchange Office
                   voiceFXS(102),      -- voice Foreign Exchange Station
                   voiceEncap(103),    -- voice encapsulation
                   voiceOverIp(104),   -- voice over IP encapsulation
                   atmDxi(105),        -- ATM DXI
                   atmFuni(106),       -- ATM FUNI
                   atmIma (107),       -- ATM IMA		   
                   pppMultilinkBundle(108), -- PPP Multilink Bundle
                   ipOverCdlc (109),   -- IBM ipOverCdlc
                   ipOverClaw (110),   -- IBM Common Link Access to Workstn
                   stackToStack (111), -- IBM stackToStack
                   virtualIpAddress (112), -- IBM VIPA
                   mpc (113),          -- IBM multi-protocol channel support
                   ipOverAtm (114),    -- IBM ipOverAtm
                   iso88025Fiber (115), -- ISO 802.5j Fiber Token Ring
                   tdlc (116),	       -- IBM twinaxial data link control
                   gigabitEthernet (117), -- Obsoleted via RFC3635
                                          -- ethernetCsmacd (6) should be used instead
                   hdlc (118),         -- HDLC
                   lapf (119),	       -- LAP F
                   v37 (120),	       -- V.37
                   x25mlp (121),       -- Multi-Link Protocol
                   x25huntGroup (122), -- X25 Hunt Group
                   transpHdlc (123),   -- Transp HDLC
                   interleave (124),   -- Interleave channel
                   fast (125),         -- Fast channel
                   ip (126),	       -- IP (for APPN HPR in IP networks)
                   docsCableMaclayer (127),  -- CATV Mac Layer
                   docsCableDownstream (128), -- CATV Downstream interface
                   docsCableUpstream (129),  -- CATV Upstream interface
                   a12MppSwitch (130), -- Avalon Parallel Processor
                   tunnel (131),       -- Encapsulation interface
                   coffee (132),       -- coffee pot
                   ces (133),          -- Circuit Emulation Service
                   atmSubInterface (134), -- ATM Sub Interface
                   l2vlan (135),       -- Layer 2 Virtual LAN using 802.1Q
                   l3ipvlan (136),     -- Layer 3 Virtual LAN using IP
                   l3ipxvlan (137),    -- Layer 3 Virtual LAN using IPX
                   digitalPowerline (138), -- IP over Power Lines	
                   mediaMailOverIp (139), -- Multimedia Mail over IP
                   dtm (140),        -- Dynamic syncronous Transfer Mode
                   dcn (141),    -- Data Communications Network
                   ipForward (142),    -- IP Forwarding Interface
                   msdsl (143),       -- Multi-rate Symmetric DSL
                   ieee1394 (144), -- IEEE1394 High Performance Serial Bus
                   if-gsn (145),       --   HIPPI-6400 
                   dvbRccMacLayer (146), -- DVB-RCC MAC Layer
                   dvbRccDownstream (147),  -- DVB-RCC Downstream Channel
                   dvbRccUpstream (148),  -- DVB-RCC Upstream Channel
                   atmVirtual (149),   -- ATM Virtual Interface
                   mplsTunnel (150),   -- MPLS Tunnel Virtual Interface
                   srp (151),	-- Spatial Reuse Protocol	
                   voiceOverAtm (152),  -- Voice Over ATM
                   voiceOverFrameRelay (153),   -- Voice Over Frame Relay 
                   idsl (154),		-- Digital Subscriber Loop over ISDN
                   compositeLink (155),  -- Avici Composite Link Interface
                   ss7SigLink (156),     -- SS7 Signaling Link 
                   propWirelessP2P (157),  --  Prop. P2P wireless interface
                   frForward (158),    -- Frame Forward Interface
                   rfc1483 (159),	-- Multiprotocol over ATM AAL5
                   usb (160),		-- USB Interface
                   ieee8023adLag (161),  -- IEEE 802.3ad Link Aggregate
                   bgppolicyaccounting (162), -- BGP Policy Accounting
                   frf16MfrBundle (163), -- FRF .16 Multilink Frame Relay 
                   h323Gatekeeper (164), -- H323 Gatekeeper
                   h323Proxy (165), -- H323 Voice and Video Proxy
                   mpls (166), -- MPLS                   
                   mfSigLink (167), -- Multi-frequency signaling link
                   hdsl2 (168), -- High Bit-Rate DSL - 2nd generation
                   shdsl (169), -- Multirate HDSL2
                   ds1FDL (170), -- Facility Data Link 4Kbps on a DS1
                   pos (171), -- Packet over SONET/SDH Interface
                   dvbAsiIn (172), -- DVB-ASI Input
                   dvbAsiOut (173), -- DVB-ASI Output 
                   plc (174), -- Power Line Communtications
                   nfas (175), -- Non Facility Associated Signaling
                   tr008 (176), -- TR008
                   gr303RDT (177), -- Remote Digital Terminal
                   gr303IDT (178), -- Integrated Digital Terminal
                   isup (179), -- ISUP
                   propDocsWirelessMaclayer (180), -- Cisco proprietary Maclayer
                   propDocsWirelessDownstream (181), -- Cisco proprietary Downstream
                   propDocsWirelessUpstream (182), -- Cisco proprietary Upstream
                   hiperlan2 (183), -- HIPERLAN Type 2 Radio Interface
                   propBWAp2Mp (184), -- PropBroadbandWirelessAccesspt2multipt
                             -- use of this iftype for IEEE 802.16 WMAN
                             -- interfaces as per IEEE Std 802.16f is
                             -- deprecated and ifType 237 should be used instead.
                   sonetOverheadChannel (185), -- SONET Overhead Channel
                   digitalWrapperOverheadChannel (186), -- Digital Wrapper
                   aal2 (187), -- ATM adaptation layer 2
                   radioMAC (188), -- MAC layer over radio links
                   atmRadio (189), -- ATM over radio links   
                   imt (190), -- Inter Machine Trunks
                   mvl (191), -- Multiple Virtual Lines DSL
                   reachDSL (192), -- Long Reach DSL
                   frDlciEndPt (193), -- Frame Relay DLCI End Point
                   atmVciEndPt (194), -- ATM VCI End Point
                   opticalChannel (195), -- Optical Channel
                   opticalTransport (196), -- Optical Transport
                   propAtm (197), --  Proprietary ATM       
                   voiceOverCable (198), -- Voice Over Cable Interface
                   infiniband (199), -- Infiniband
                   teLink (200), -- TE Link
                   q2931 (201), -- Q.2931
                   virtualTg (202), -- Virtual Trunk Group
                   sipTg (203), -- SIP Trunk Group
                   sipSig (204), -- SIP Signaling   
                   docsCableUpstreamChannel (205), -- CATV Upstream Channel
                   econet (206), -- Acorn Econet
                   pon155 (207), -- FSAN 155Mb Symetrical PON interface
                   pon622 (208), -- FSAN622Mb Symetrical PON interface
                   bridge (209), -- Transparent bridge interface
                   linegroup (210), -- Interface common to multiple lines   
                   voiceEMFGD (211), -- voice E&M Feature Group D
                   voiceFGDEANA (212), -- voice FGD Exchange Access North American
                   voiceDID (213), -- voice Direct Inward Dialing
                   mpegTransport (214), -- MPEG transport interface
                   sixToFour (215), -- 6to4 interface (DEPRECATED)
                   gtp (216), -- GTP (GPRS Tunneling Protocol)
                   pdnEtherLoop1 (217), -- Paradyne EtherLoop 1
                   pdnEtherLoop2 (218), -- Paradyne EtherLoop 2
                   opticalChannelGroup (219), -- Optical Channel Group
                   homepna (220), -- HomePNA ITU-T G.989
                   gfp (221), -- Generic Framing Procedure (GFP)
                   ciscoISLvlan (222), -- Layer 2 Virtual LAN using Cisco ISL
                   actelisMetaLOOP (223), -- Acteleis proprietary MetaLOOP High Speed Link 
                   fcipLink (224), -- FCIP Link 
                   rpr (225), -- Resilient Packet Ring Interface Type
                   qam (226), -- RF Qam Interface
                   lmp (227), -- Link Management Protocol
                   cblVectaStar (228), -- Cambridge Broadband Networks Limited VectaStar
                   docsCableMCmtsDownstream (229), -- CATV Modular CMTS Downstream Interface
                   adsl2 (230), -- Asymmetric Digital Subscriber Loop Version 2 
                                -- (DEPRECATED/OBSOLETED - please use adsl2plus 238 instead)
                   macSecControlledIF (231), -- MACSecControlled 
                   macSecUncontrolledIF (232), -- MACSecUncontrolled
                   aviciOpticalEther (233), -- Avici Optical Ethernet Aggregate
                   atmbond (234), -- atmbond
                   voiceFGDOS (235), -- voice FGD Operator Services
                   mocaVersion1 (236), -- MultiMedia over Coax Alliance (MoCA) Interface
                             -- as documented in information provided privately to IANA
                   ieee80216WMAN (237), -- IEEE 802.16 WMAN interface
                   adsl2plus (238), -- Asymmetric Digital Subscriber Loop Version 2, 
                                   -- Version 2 Plus and all variants
                   dvbRcsMacLayer (239), -- DVB-RCS MAC Layer
                   dvbTdm (240), -- DVB Satellite TDM
                   dvbRcsTdma (241), -- DVB-RCS TDMA
                   x86Laps (242), -- LAPS based on ITU-T X.86/Y.1323
                   wwanPP (243), -- 3GPP WWAN
                   wwanPP2 (244), -- 3GPP2 WWAN
                   voiceEBS (245), -- voice P-phone EBS physical interface
                   ifPwType (246), -- Pseudowire interface type
                   ilan (247), -- Internal LAN on a bridge per IEEE 802.1ap
                   pip (248), -- Provider Instance Port on a bridge per IEEE 802.1ah PBB
                   aluELP (249), -- Alcatel-Lucent Ethernet Link Protection
                   gpon (250), -- Gigabit-capable passive optical networks (G-PON) as per ITU-T G.948
                   vdsl2 (251), -- Very high speed digital subscriber line Version 2 (as per ITU-T Recommendation G.993.2)
                   capwapDot11Profile (252), -- WLAN Profile Interface
                   capwapDot11Bss (253), -- WLAN BSS Interface
                   capwapWtpVirtualRadio (254), -- WTP Virtual Radio Interface
                   bits (255), -- bitsport
                   docsCableUpstreamRfPort (256), -- DOCSIS CATV Upstream RF Port
                   cableDownstreamRfPort (257) -- CATV downstream RF port
                   }

IANAtunnelType ::= TEXTUAL-CONVENTION
    STATUS     current
    DESCRIPTION
            "The encapsulation method used by a tunnel. The value
            direct indicates that a packet is encapsulated
            directly within a normal IP header, with no
            intermediate header, and unicast to the remote tunnel
            endpoint (e.g., an RFC 2003 IP-in-IP tunnel, or an RFC
            1933 IPv6-in-IPv4 tunnel). The value minimal indicates
            that a Minimal Forwarding Header (RFC 2004) is
            inserted between the outer header and the payload
            packet. The value UDP indicates that the payload
            packet is encapsulated within a normal UDP packet
            (e.g., RFC 1234).

            The values sixToFour, sixOverFour, and isatap
            indicates that an IPv6 packet is encapsulated directly
            within an IPv4 header, with no intermediate header,
            and unicast to the destination determined by the 6to4,
            6over4, or ISATAP protocol.

            The remaining protocol-specific values indicate that a
            header of the protocol of that name is inserted
            between the outer header and the payload header.

            The assignment policy for IANAtunnelType values is
            identical to the policy for assigning IANAifType
            values."
    SYNTAX     INTEGER {
                   other(1),        -- none of the following
                   direct(2),       -- no intermediate header
                   gre(3),          -- GRE encapsulation
                   minimal(4),      -- Minimal encapsulation
                   l2tp(5),         -- L2TP encapsulation
                   pptp(6),         -- PPTP encapsulation
                   l2f(7),          -- L2F encapsulation
                   udp(8),          -- UDP encapsulation
                   atmp(9),         -- ATMP encapsulation
                   msdp(10),        -- MSDP encapsulation
                   sixToFour(11),   -- 6to4 encapsulation
                   sixOverFour(12), -- 6over4 encapsulation
                   isatap(13),      -- ISATAP encapsulation
                   teredo(14),      -- Teredo encapsulation
                   ipHttps(15)      -- IPHTTPS
               }
	
RemoteAuthServerType ::= TEXTUAL-CONVENTION 
  STATUS      current 
  DESCRIPTION 
	 "This indicates which Remote Server is to provide the 
	  authentication. Currently supported servers are RADIUS
	  Server and Terminal Access Controller Access-Control 
	  System Plus (TACACS+) Server." 
  SYNTAX      INTEGER {                           
				  radiusServer(1), 
				  tacacsplusServer(2) 
			  }

Ipv6Address ::= TEXTUAL-CONVENTION
             DISPLAY-HINT "2x:"
             STATUS       current
             DESCRIPTION
               "This data type is used to model IPv6 addresses.
                This is a binary string of 16 octets in network
                byte-order."
             SYNTAX       OCTET STRING (SIZE (16))
			 
RmonStatus ::= TEXTUAL-CONVENTION
     STATUS current
     DESCRIPTION
         "The status of a table entry.

         Setting this object to the value invalid(4) has the
         effect of invalidating the corresponding entry.
         That is, it effectively disassociates the mapping
         identified with said entry.
         It is an implementation-specific matter as to whether
         the agent removes an invalidated entry from the table.
         Accordingly, management stations must be prepared to
         receive tabular information from agents that corresponds
         to entries currently not in use.  Proper
         interpretation of such entries requires examination
         of the relevant EntryStatus object.

         An existing instance of this object cannot be set to
         createRequest(2).  This object may only be set to
         createRequest(2) when this instance is created.  When
         this object is created, the agent may wish to create
         supplemental object instances with default values
         to complete a conceptual row in this table.  Because the

         creation of these default objects is entirely at the option
         of the agent, the manager must not assume that any will be
         created, but may make use of any that are created.
         Immediately after completing the create operation, the agent
         must set this object to underCreation(3).

         When in the underCreation(3) state, an entry is allowed to
         exist in a possibly incomplete, possibly inconsistent state,
         usually to allow it to be modified in multiple PDUs.  When in
         this state, an entry is not fully active.
         Entries shall exist in the underCreation(3) state until
         the management station is finished configuring the entry
         and sets this object to valid(1) or aborts, setting this
         object to invalid(4).  If the agent determines that an
         entry has been in the underCreation(3) state for an
         abnormally long time, it may decide that the management
         station has crashed.  If the agent makes this decision,
         it may set this object to invalid(4) to reclaim the
         entry.  A prudent agent will understand that the
         management station may need to wait for human input
         and will allow for that possibility in its
         determination of this abnormally long period.

         An entry in the valid(1) state is fully configured and
         consistent and fully represents the configuration or
         operation such a row is intended to represent.  For
         example, it could be a statistical function that is
         configured and active, or a filter that is available
         in the list of filters processed by the packet capture
         process.

         A manager is restricted to changing the state of an entry in
         the following ways:

              To:       valid  createRequest  underCreation  invalid
         From:
         valid             OK             NO             OK       OK
         createRequest    N/A            N/A            N/A      N/A
         underCreation     OK             NO             OK       OK
         invalid           NO             NO             NO       OK
         nonExistent       NO             OK             NO       OK

         In the table above, it is not applicable to move the state
         from the createRequest state to any other state because the
         manager will never find the variable in that state.  The
         nonExistent state is not a value of the enumeration, rather
         it means that the entryStatus variable does not exist at all.

         An agent may allow an entryStatus variable to change state in
         additional ways, so long as the semantics of the states are
         followed.  This allowance is made to ease the implementation of
         the agent and is made despite the fact that managers should
         never exercise these additional state transitions."
     SYNTAX INTEGER {
                valid(1),
                createRequest(2),
                underCreation(3),
                invalid(4)
            }
Dscp ::= TEXTUAL-CONVENTION
    DISPLAY-HINT "d"
    STATUS   current
    DESCRIPTION
       "A Differentiated Services Code-Point that may be used for
       marking a traffic stream."
    REFERENCE
        "RFC 2474, RFC 2780"
    SYNTAX   Integer32 (0..63)	
-- ----------------------------------------------------------------- -- 
-- groups in the MIB  
-- ----------------------------------------------------------------- -- 

	sysAdministration				OBJECT IDENTIFIER ::= { teg30284 1 }
	sysACL				OBJECT IDENTIFIER ::= { teg30284 2 }
	sysBandWidthCtrl				OBJECT IDENTIFIER ::= { teg30284 3 }
	sysDHCPSnoop				OBJECT IDENTIFIER ::= { teg30284 4 }
	sysFwdTable				OBJECT IDENTIFIER ::= { teg30284 5 }
	sysGVRP				OBJECT IDENTIFIER ::= { teg30284 6 }
	sysLA				OBJECT IDENTIFIER ::= { teg30284 7 }
	sysLBD				OBJECT IDENTIFIER ::= { teg30284 8 }
	sysLLDP				OBJECT IDENTIFIER ::= { teg30284 9 }
	sysMirror				OBJECT IDENTIFIER ::= { teg30284 10 }
	sysMulticast				OBJECT IDENTIFIER ::= { teg30284 11 }
	sysPhyInf				OBJECT IDENTIFIER ::= { teg30284 12 }
	sysPrivateVLAN				OBJECT IDENTIFIER ::= { teg30284 13 }
	sysQoS				OBJECT IDENTIFIER ::= { teg30284 14 }
	sysRMON				OBJECT IDENTIFIER ::= { teg30284 15 }
	sysSystem				OBJECT IDENTIFIER ::= { teg30284 16 }
	sysSystemInfo				OBJECT IDENTIFIER ::= { sysSystem 1 }
	sysSystemCtrl				OBJECT IDENTIFIER ::= { sysSystem 2 }
	sysIPv4SysSettings				OBJECT IDENTIFIER ::= { sysSystem 3 }
	sysIPv6SysSettings				OBJECT IDENTIFIER ::= { sysSystem 4 }
	sysIPv6Neighbor				OBJECT IDENTIFIER ::= { sysSystem 5 }
	sysSmartFan				OBJECT IDENTIFIER ::= { sysSystem 6 }
	sysSNMP				OBJECT IDENTIFIER ::= { teg30284 17 }
	sysSNTP				OBJECT IDENTIFIER ::= { teg30284 18 }
	sysSTP				OBJECT IDENTIFIER ::= { teg30284 19 }
	sysSecurity				OBJECT IDENTIFIER ::= { teg30284 20 }
	sysPNAC				OBJECT IDENTIFIER ::= { sysSecurity 1 }
	sysPNACAuthServer				OBJECT IDENTIFIER ::= { sysSecurity 2 }
	sysRadius				OBJECT IDENTIFIER ::= { sysSecurity 3 }
	sysTacacs				OBJECT IDENTIFIER ::= { sysSecurity 4 }
	sysSSL				OBJECT IDENTIFIER ::= { sysSecurity 5 }
	sysIPAccessList				OBJECT IDENTIFIER ::= { sysSecurity 8 }
	sysMACFilter				OBJECT IDENTIFIER ::= { sysSecurity 9 }
	sysStormCtrl				OBJECT IDENTIFIER ::= { teg30284 21 }
	sysSyslog				OBJECT IDENTIFIER ::= { teg30284 22 }
	sysStatistics				OBJECT IDENTIFIER ::= { teg30284 23 }
	sysTools				OBJECT IDENTIFIER ::= { teg30284 24 }
	sysVLAN				OBJECT IDENTIFIER ::= { teg30284 25 }
	sysVoiceVlan				OBJECT IDENTIFIER ::= { teg30284 26 }
	sysDos				OBJECT IDENTIFIER ::= { teg30284 27 }
	sysDNS				OBJECT IDENTIFIER ::= { teg30284 28 }
      
-- ---------------------------------------------------------------- --

	-- ----------------------------------------------------------------
    -- The IP Access list group
    -- ----------------------------------------------------------------
	ipAccListGlobal          OBJECT IDENTIFIER ::= { sysIPAccessList 1 }
   
	ipAccListStatus		OBJECT-TYPE 
	   SYNTAX      INTEGER {
						  enabled      (1),
						  disabled	   (2)
					   }
	   MAX-ACCESS  read-write 
	   STATUS      current 
	   DESCRIPTION 
			   "This object indicates trusted host function is enabled or disabled. 
					When trusted host function is enabled, Smart Switches will 
					only allow hosts which you trust to access and control the switch.
					Your local host IP Addresses must be one of the IP Addresses to 
					avoid disconnection." 
		
	   DEFVAL  { disabled }    
	   ::= { ipAccListGlobal 1}
	
	ipAccListTable OBJECT-TYPE
	   SYNTAX      SEQUENCE OF IpAccListEntry
	   MAX-ACCESS  not-accessible
	   STATUS      current
	   DESCRIPTION
		   "A table to configure IP authorized managers in the system."
	   ::= { sysIPAccessList 2 }

	ipAccListEntry OBJECT-TYPE
	   SYNTAX      IpAccListEntry
	   MAX-ACCESS  not-accessible
	   STATUS      current
	   DESCRIPTION
		   "Each entry in this table represents rules for particular
			IP authorized manager."
	   INDEX { ipAccListIpAddrType,ipAccListIpAddr}
	   ::= { ipAccListTable 1 }

	IpAccListEntry ::=
	   SEQUENCE {
		  ipAccListIpAddrType
			INTEGER,
		  ipAccListIpAddr
			 InetAddress,
		  ipAccListRowStatus
			 RowStatus
	 }
	
	ipAccListIpAddrType OBJECT-TYPE
	SYNTAX INTEGER {
				ipv4 (1),
				ipv6 (2)
			}
	MAX-ACCESS read-only
	STATUS current
	DESCRIPTION
		"The IP address type of the ip access list
				 referred to in this table entry."
	::=  { ipAccListEntry 1 }
			
	ipAccListIpAddr OBJECT-TYPE
	   SYNTAX      InetAddress
	   MAX-ACCESS  read-only
	   STATUS      current
	   DESCRIPTION
		   "Specifies either the Network or Host address from which the switch
			can be managed.
			An address 0.0.0.0 indicates 'Any Manager'."
	   ::= { ipAccListEntry 2 }

	ipAccListRowStatus OBJECT-TYPE
	   SYNTAX      RowStatus
		MAX-ACCESS  read-create
	   STATUS      current
	   DESCRIPTION
		  "This object indicates the status of this entry."
	   ::= { ipAccListEntry 3 }
	   
	
-- sysSystemCtrl

	systemSwitchBaseMacAddress OBJECT-TYPE 
		SYNTAX      MacAddress
		MAX-ACCESS  read-only 
		STATUS      current 
		DESCRIPTION 
			"Ethernet address (base address) of the Switch.
			 This base Mac Address, if modified, will take effect only when the
			 Switch is restarted."

--		DEFVAL  { '000102030405'h }
		::= { sysSystemCtrl 1 }
	   
	systemWebAutoTimeoutInterval  OBJECT-TYPE
		SYNTAX      Integer32 (3..60)
		UNITS       "minutes"
		MAX-ACCESS  read-write
		STATUS      current
		DESCRIPTION
			"This time interval is used to count the time and
			 logout web interface automatically."  
		::= { sysSystemCtrl 2 } 

	systemHttpStatus  OBJECT-TYPE
	    SYNTAX       INTEGER {
					enabled(1),
					disabled(2)
				   }
	    MAX-ACCESS  read-only
	    STATUS      current
	    DESCRIPTION
		   "This object is for enabling or disabling HTTP in the system."

	    DEFVAL  { enabled }
	    ::= { sysSystemCtrl 3 }      
   
		
	systemDhcpAutoConfig OBJECT-TYPE 
		SYNTAX      INTEGER {
		              enabled(1),
		              disabled(2)
				   }
		MAX-ACCESS  read-write 
		STATUS      current 
		DESCRIPTION 
		   "Enables/Disables the DHCP Auto Config."
		DEFVAL  { disabled }
		::= { sysSystemCtrl 4 }
	
-- sysIPv4SysSettings
    ipv4sysIpAddrCfgMode OBJECT-TYPE 
       SYNTAX      INTEGER {
                    manual(1),
                    dhcp(2)
                   }
       MAX-ACCESS  read-write 
       STATUS      current 
       DESCRIPTION 
          "Specifies the means by which the default interface in the device 
 	
			gets the IP address.
			
			If 'manual' mode is selected, the default interface takes the 
			'ipv4sysIpAddr' configured in the system.
			
			If 'dhcp' mode is selected, the default interface gets the IP address
			through DHCP Client etc.
			If the system fails to get the IP address dynamically through all the
			above protocols, the default interface uses the 'ipv4sysIpAddr' 
			configured in the system."  
       DEFVAL  { manual } 
       ::= { sysIPv4SysSettings 1 }

    ipv4sysIpAddr  OBJECT-TYPE
       SYNTAX      IpAddress
       MAX-ACCESS  read-write
       STATUS      current
       DESCRIPTION 
          "Default IP Address of the system.
		  
           This IP address, if modified, will take effect only when the 
           configuration is stored & restored."
       ::= { sysIPv4SysSettings 2 }
    
    ipv4SysIpSubnetMask  OBJECT-TYPE
       SYNTAX      IpAddress
       MAX-ACCESS  read-write
       STATUS      current
       DESCRIPTION 
          "IP subnet mask for the default IP address.
    
           This subnet mask, if modified, will take effect only when the
           configuration is stored & restored."
       ::= { sysIPv4SysSettings 3 }

    ipv4SysGateway  OBJECT-TYPE
       SYNTAX      IpAddress
       MAX-ACCESS  read-write
       STATUS      current
       DESCRIPTION 
          "Gateway"
       ::= { sysIPv4SysSettings 4 }
	   

 -- System infomation 

	sysInfoUpTime OBJECT-TYPE
		SYNTAX      TimeTicks
		MAX-ACCESS  read-only
		STATUS      current
		DESCRIPTION
			"The time (in hundredths of a second) since the
			network management portion of the system was last
			re-initialized."
		::= { sysSystemInfo 1 }

	sysInfoFirmwareVersion OBJECT-TYPE
		SYNTAX      DisplayString (SIZE(1..15))
		MAX-ACCESS  read-only
		STATUS      current
		DESCRIPTION
			"Version number of the Firmware."
		DEFVAL { "" }
		::= { sysSystemInfo 2 }

	sysInfoBootloaderVersion OBJECT-TYPE
		SYNTAX      DisplayString (SIZE(1..15))
		MAX-ACCESS  read-only
		STATUS      current
		DESCRIPTION
			"Version number of the Firmware."
		DEFVAL { "" }
		::= { sysSystemInfo 3 }
		
	--sysInfoHardwareVersion OBJECT-TYPE
	--	SYNTAX      DisplayString (SIZE(1..15))
	--	MAX-ACCESS  read-only
	--	STATUS      current
	--	DESCRIPTION
	--		"Version number of the Hardware."
	--	DEFVAL { "" }
	--	::= { sysSystemInfo 4 }

	sysInfoDramSize OBJECT-TYPE
		SYNTAX      Unsigned32
		MAX-ACCESS  read-only
		STATUS      current
		DESCRIPTION "This is the DRAM size in Millionbytes."
		::= { sysSystemInfo 5 }

	sysInfoFlashSize OBJECT-TYPE
		SYNTAX      Unsigned32
		MAX-ACCESS  read-only
		STATUS      current
		DESCRIPTION "This is the Flash size in Millionbytes."
		::= { sysSystemInfo 6 }

	sysInfoDescr OBJECT-TYPE
		SYNTAX      DisplayString (SIZE (0..255))
		MAX-ACCESS  read-only
		STATUS      current
		DESCRIPTION
				"A textual description used to identify the device."
		::= { sysSystemInfo 7 }

	sysInfoObjectID OBJECT-TYPE
		SYNTAX      OBJECT IDENTIFIER
		MAX-ACCESS  read-only
		STATUS      current
		DESCRIPTION
				"The vendor's authoritative identification of the
				network management subsystem contained in the entity.
				This value is allocated within the SMI enterprises
				subtree (1.3.6.1.4.1) and provides an easy and
				unambiguous means for determining `what kind of box' is
				being managed.  For example, if vendor `Flintstones,
				Inc.' was assigned the subtree 1.3.6.1.4.1.424242,
				it could assign the identifier 1.3.6.1.4.1.424242.1.1
				to its `Fred Router'."
		::= { sysSystemInfo 8 }	   

	sysInfoSysName OBJECT-TYPE
		SYNTAX      DisplayString (SIZE(0..15))
		MAX-ACCESS  read-write
		STATUS      current
		DESCRIPTION
			"System name used for identification of the device."
		DEFVAL { "SysName" }
		::= { sysSystemInfo 9 }

	sysInfoSysLocation OBJECT-TYPE
	   SYNTAX      DisplayString (SIZE(0..30))
	   MAX-ACCESS  read-write
	   STATUS      current
	   DESCRIPTION
		  "The physical location of this node (e.g., `telsyshone
		   closet, 3rd floor').  If the location is unknown, the value
		   is the zero-length string."
	   ::= { sysSystemInfo 10 }

	sysInfoSysContact OBJECT-TYPE
		SYNTAX      DisplayString (SIZE (0..30))
		MAX-ACCESS  read-write
		STATUS      current
		DESCRIPTION
				"The textual identification of the contact person for
				this managed node, together with information on how
				to contact this person.  If no contact information is
				known, the value is the zero-length string."
		::= { sysSystemInfo 11 }


	-- DHCP Snooping Global Settings
	dhcpSnpGeneralGroup              	OBJECT IDENTIFIER ::= { sysDHCPSnoop 1 }
	
	dhcpSnpSystemStatus OBJECT-TYPE
		SYNTAX      INTEGER {
						enabled(1),
						disabled(2)
					}
		MAX-ACCESS  read-write
		STATUS      current
		DESCRIPTION
			"Enable/Disable DHCP Snooping."
		DEFVAL { disabled }
		::= { dhcpSnpGeneralGroup 1 }

	dhcpSnpVerifyMACAddr OBJECT-TYPE
		SYNTAX      INTEGER {
						enabled(1),
						disabled(2)
					}
		MAX-ACCESS  read-write
		STATUS      current
		DESCRIPTION
			"Determine if to verify MAC address for incoming DHCP packets."
		DEFVAL { enabled }
		::= { dhcpSnpGeneralGroup 2 }

	dhcpSnpOption82Insertion OBJECT-TYPE
		SYNTAX      INTEGER {
						enabled(1),
						disabled(2)
					}
		MAX-ACCESS  read-write
		STATUS      current
		DESCRIPTION
			"Determine if to insert DHCP option 82 into packets."
		DEFVAL { disabled }
		::= { dhcpSnpGeneralGroup 3 }

	dhcpSnpPassThroughOption82 OBJECT-TYPE
		SYNTAX      INTEGER {
						enabled(1),
						disabled(2)
					}
		MAX-ACCESS  read-write
		STATUS      current
		DESCRIPTION
			"Determine if to pass through DHCP packets with option 82."
		DEFVAL { disabled }
		::= { dhcpSnpGeneralGroup 4 }

	dhcpSnpBackupDatabase OBJECT-TYPE
		SYNTAX      INTEGER {
						enabled(1),
						disabled(2)
					}
		MAX-ACCESS  read-write
		STATUS      current
		DESCRIPTION
			"Determine if to backup database to flash memory."
		DEFVAL { disabled }
		::= { dhcpSnpGeneralGroup 5 }

	dhcpSnpBackupDatabaseInterval OBJECT-TYPE
		SYNTAX      Integer32 (600..86400)
		MAX-ACCESS  read-write
		STATUS      current
		DESCRIPTION
			"Determine the period to backup database."
		DEFVAL { 1200 }
		::= { dhcpSnpGeneralGroup 6 }


	-- 	DHCP Snooping VLAN Settings
		   
	dhcpSnpVlanTable OBJECT-TYPE
		SYNTAX      SEQUENCE OF DhcpSnpVlanEntry
		MAX-ACCESS  not-accessible
		STATUS      current
		DESCRIPTION
			"A table of DHCP snooping VLAN settings."
		::= { sysDHCPSnoop 2 }

	dhcpSnpVlanEntry OBJECT-TYPE
		SYNTAX      DhcpSnpVlanEntry
		MAX-ACCESS  not-accessible
		STATUS      current
		DESCRIPTION
			"The entry of DHCP snooping VLAN setting table."
		INDEX { dhcpSnpVlanId }
		::= { dhcpSnpVlanTable 1 }

	DhcpSnpVlanEntry ::= SEQUENCE
	{
		dhcpSnpVlanId			Unsigned32,
		dhcpSnpVlanStatus		INTEGER,
		dhcpSnpVlanRowStatus	RowStatus
	}

	dhcpSnpVlanId OBJECT-TYPE
		SYNTAX      Unsigned32 (1..4093)
		MAX-ACCESS  read-only
		STATUS      current
		DESCRIPTION
			"The VLAN ID."
		::= { dhcpSnpVlanEntry 1 }

	dhcpSnpVlanStatus OBJECT-TYPE
		SYNTAX      INTEGER {
						enabled(1),
						disabled(2)
					}
		MAX-ACCESS  read-write
		STATUS      current
		DESCRIPTION
			"The VLAN status."
		::= { dhcpSnpVlanEntry 2 }

	dhcpSnpVlanRowStatus OBJECT-TYPE
		SYNTAX      RowStatus
		MAX-ACCESS  read-create
		STATUS      current
		DESCRIPTION
			"The VLAN row status."
		::= { dhcpSnpVlanEntry 3 }

	-- DHCP Snooping trusted port settings
	dhcpSnpPortTable OBJECT-TYPE
		SYNTAX      SEQUENCE OF DhcpSnpPortEntry
		MAX-ACCESS  not-accessible
		STATUS      current
		DESCRIPTION
			"A table of DHCP snooping port settings."
		::= { sysDHCPSnoop 3 }

	dhcpSnpPortEntry OBJECT-TYPE
		SYNTAX      DhcpSnpPortEntry
		MAX-ACCESS  not-accessible
		STATUS      current
		DESCRIPTION
			"The entry of DHCP snooping port setting table."
		INDEX { dhcpSnpPortIndex }
		::= { dhcpSnpPortTable 1 }

	DhcpSnpPortEntry ::=SEQUENCE 
	{
		dhcpSnpPortIndex	Integer32,
		dhcpSnpPortStatus	INTEGER
	}

	dhcpSnpPortIndex OBJECT-TYPE
		SYNTAX      Integer32 (1..65535)
		MAX-ACCESS  read-only
		STATUS      current
		DESCRIPTION
			"The port number."
		::= { dhcpSnpPortEntry 1 }

	dhcpSnpPortStatus OBJECT-TYPE
		SYNTAX      INTEGER {
						trusted(1),
						untrusted(2)
					}
		MAX-ACCESS  read-write
		STATUS      current
		DESCRIPTION
			"The port status."
		DEFVAL {trusted}
		::= { dhcpSnpPortEntry 2 }
	

	-- DHCP Snooping Database Banding Settings
		   
	dhcpSnpDbBindingTable OBJECT-TYPE
		SYNTAX      SEQUENCE OF DhcpSnpDbBindingEntry
		MAX-ACCESS  not-accessible
		STATUS      current
		DESCRIPTION
			"A table of DHCP snooping bindind database."
		::= { sysDHCPSnoop 4 }

	dhcpSnpDbBindingEntry OBJECT-TYPE
		SYNTAX      DhcpSnpDbBindingEntry
		MAX-ACCESS  not-accessible
		STATUS      current
		DESCRIPTION
			"The entry of DHCP snooping bindind database table."
		INDEX { dhcpSnpDbVlanId,  dhcpSnpDbMacAddr, dhcpSnpDbIPAddr}
		::= { dhcpSnpDbBindingTable 1 }

	DhcpSnpDbBindingEntry ::= SEQUENCE 
	{
			dhcpSnpDbVlanId		Unsigned32,
			dhcpSnpDbMacAddr	MacAddress,
			dhcpSnpDbIPAddr		InetAddress,
			dhcpSnpDbType		INTEGER,
			dhcpSnpDbPort		DisplayString,
			dhcpSnpDbLeaseTime	Unsigned32,
			dhcpSnpDbRowStatus	RowStatus
		}

	dhcpSnpDbVlanId OBJECT-TYPE
		SYNTAX      Unsigned32 (1..4093)
		MAX-ACCESS  read-only
		STATUS      current
		DESCRIPTION
			"The VLAN ID."
		::= { dhcpSnpDbBindingEntry 1 }
		
	dhcpSnpDbMacAddr OBJECT-TYPE
		SYNTAX      MacAddress
		MAX-ACCESS  read-only
		STATUS      current
		DESCRIPTION
			"The MAC address."
		::= { dhcpSnpDbBindingEntry 2 }
		
	dhcpSnpDbIPAddr OBJECT-TYPE
		SYNTAX      InetAddress
		MAX-ACCESS  read-only
		STATUS      current
		DESCRIPTION
			"The IP address, supported ipv4 and ipv6."
		::= { dhcpSnpDbBindingEntry 3 }

	dhcpSnpDbType OBJECT-TYPE
		SYNTAX      INTEGER {
					 static (1),
					 learning (2),
					 dynamic (3)
				   }
		MAX-ACCESS  read-write
		STATUS      current
		DESCRIPTION
			"The entry type dynamic or static ."
		::= { dhcpSnpDbBindingEntry 4 }

	dhcpSnpDbPort OBJECT-TYPE
		SYNTAX      DisplayString
		MAX-ACCESS  read-write
		STATUS      current
		DESCRIPTION
			"The port name.
			In order to display LA port,
			use displaystring type,thus LA group 1 will
			be displayed as po1,group 2 will be displayed
			as po2,etc."
		::= { dhcpSnpDbBindingEntry 5 }

	dhcpSnpDbLeaseTime OBJECT-TYPE
		SYNTAX      Unsigned32(10..4294967295)
		MAX-ACCESS  read-write
		STATUS      current
		DESCRIPTION
			"The DHCP lease time."
		::= { dhcpSnpDbBindingEntry 6 }

	dhcpSnpDbRowStatus OBJECT-TYPE
		SYNTAX      RowStatus
		MAX-ACCESS  read-write
		STATUS      current
		DESCRIPTION
			"The entry row status."
		::= { dhcpSnpDbBindingEntry 7 }
		
	-- DHCP Snooping traps
	dhcpSnpTraps              	OBJECT IDENTIFIER ::= { sysDHCPSnoop 5 }
	
 	recvPktFromUntrustPort NOTIFICATION-TYPE
      OBJECTS {
      dhcpSnpPortIndex
              }
      STATUS             current
      DESCRIPTION
       "This is a Trap that will send to snmp ,and it will Generated when  Untrust Port recv Pkt's "
 	::= {dhcpSnpTraps 1 }
	
 	getIpFromUntrustPort NOTIFICATION-TYPE
      OBJECTS {
      dhcpSnpDbPort,
	  dhcpSnpDbMacAddr,
	  dhcpSnpDbIPAddr
              }
      STATUS             current
      DESCRIPTION
       "This is a trap that will send to snmp manager,and it will be generated when the ip address got from an untrust port."
 	::= {dhcpSnpTraps 2 }
	
 	dbExpired NOTIFICATION-TYPE
      OBJECTS {
	  dhcpSnpDbVlanId,
	  dhcpSnpDbMacAddr,
	  dhcpSnpDbIPAddr,
	  dhcpSnpDbPort
              }
      STATUS             current
      DESCRIPTION
       "This is a trap that will send to snmp manager,and it will be generated when the ipdb binding entry is expired."
 	::= {dhcpSnpTraps 3 }
	
 	dbIpIncorrect NOTIFICATION-TYPE
      OBJECTS {
	  dhcpSnpDbVlanId,
	  dhcpSnpDbMacAddr,
	  dhcpSnpDbIPAddr,
	  dhcpSnpDbPort
              }
      STATUS             current
      DESCRIPTION
       "This is a trap that will send to snmp manager,and it will be generated when ip address learnt is not the same
	    as the one of existed static/dynamic bingding entry."
 	::= {dhcpSnpTraps 4 }
	
 	dbPortIncorrect NOTIFICATION-TYPE
      OBJECTS {
	  dhcpSnpDbVlanId,
	  dhcpSnpDbMacAddr,
	  dhcpSnpDbIPAddr,
	  dhcpSnpDbPort
              }
      STATUS             current
      DESCRIPTION
       "This is a trap that will send to snmp manager,and it will be generated when the port where the ip address was 
	   learnt is not the same as the one of existed static/dynamic bingding entry."
 	::= {dhcpSnpTraps 5 }
	
 	dbVlanIncorrect NOTIFICATION-TYPE
      OBJECTS {
	  dhcpSnpDbVlanId,
	  dhcpSnpDbMacAddr,
	  dhcpSnpDbIPAddr,
	  dhcpSnpDbPort
              }
      STATUS             current
      DESCRIPTION
       "This is a trap that will send to snmp manager,and it will be generated when the vlan where the ip address was 
	   learnt is not the same as the one of existed static/dynamic bingding entry."
 	::= {dhcpSnpTraps 6 }
	-- Global settings
	mirrorStatus OBJECT-TYPE 
		SYNTAX      INTEGER {
					  enabled(1),
					  disabled(2)
				   }
		MAX-ACCESS  read-write 
		STATUS      current 
		DESCRIPTION 
		   "This object is used to enable/disable mirroring
			feature in hardware.
			When set to 'disabled (2)', all mirroring configurations will be
			removed from hardware.
			When set to 'enabled (1)', all mirroring configurations
			present in software will be programmed in hardware."
		DEFVAL  { disabled }
		::= { sysMirror 1 }

	mirrorToPort OBJECT-TYPE 
		SYNTAX      Integer32
		MAX-ACCESS  read-write 
		STATUS      current 
		DESCRIPTION 
			"Specifies the port to which the active mirrored traffic controlled
			by issMirrorCtrlTable is to be copied."
	   ::= { sysMirror 2 }

	mirrorIngressPortList OBJECT-TYPE 
	   SYNTAX      PortList 
	   MAX-ACCESS  read-write 
	   STATUS      current 
	   DESCRIPTION 
		   "Provides control to enable or disable mirroring of ingress 
			traffic over this interface to the mirrored-to port."
	   ::= { sysMirror 3 }

	mirrorEgressPortList OBJECT-TYPE 
	   SYNTAX      PortList
	   MAX-ACCESS  read-write 
	   STATUS      current 
	   DESCRIPTION 
		   "Provides control to enable or disable mirroring of egress 
			traffic over this interface to the mirrored-to port."
	   ::= { sysMirror 4 }
	-- Mirror source port configuration Table

--	mirrorCtrlTable OBJECT-TYPE 
--		SYNTAX      SEQUENCE OF MirrorCtrlEntry 
--		MAX-ACCESS  not-accessible 
--		STATUS      current 
--		DESCRIPTION 
--		  "A table to control mirroring features for each interface 
--		   in the switch.
--		   Parameters in this table are valid only when the 
--		   'mirrorStatus' for the switch is not 'disabled'."
--		::= { sysMirror 3 }

--	mirrorCtrlEntry OBJECT-TYPE 
--		SYNTAX      MirrorCtrlEntry 
--		MAX-ACCESS  not-accessible 
--		STATUS      current 
--		DESCRIPTION 
--			"An entry appears in this table for each interface 
--			in the system."
--		INDEX { mirrorCtrlIndex }
--		::= { mirrorCtrlTable 1 }
	   
--	MirrorCtrlEntry ::= 
--		SEQUENCE { 
--			mirrorCtrlIndex	
--				Integer32, 
--			mirrorCtrlIngressMirroring 
--				INTEGER, 
--			mirrorCtrlEgressMirroring 
--				INTEGER,
--			mirrorCtrlStatus 
--				INTEGER 
--	  }

--	mirrorCtrlIndex OBJECT-TYPE 
--	   SYNTAX      Integer32 (1..65535)
--	   MAX-ACCESS  read-only 
--	   STATUS      current 
--	   DESCRIPTION 
--		  "The interface index of the port for which the configuration
--		  in this entry applies."
--	   ::= { mirrorCtrlEntry 1 }
		
--	mirrorCtrlIngressMirroring OBJECT-TYPE 
--	   SYNTAX      INTEGER {
--				   enabled(1),
--				   disabled(2)
--				   }
--	   MAX-ACCESS  read-write 
--	   STATUS      current 
--	   DESCRIPTION 
--		   "Provides control to enable or disable mirroring of ingress 
--			traffic over this interface to the mirrored-to port."
--	   DEFVAL  { disabled }
--	   ::= { mirrorCtrlEntry 2 }

--	mirrorCtrlEgressMirroring OBJECT-TYPE 
--	   SYNTAX      INTEGER {
--				   enabled(1),
--				   disabled(2)
--				  }
--	   MAX-ACCESS  read-write 
--	   STATUS      current 
--	   DESCRIPTION 
--		   "Provides control to enable or disable mirroring of egress 
--			traffic over this interface to the mirrored-to port."
--	   DEFVAL  { disabled }
--	   ::= { mirrorCtrlEntry 3 }
	   
--	mirrorCtrlStatus OBJECT-TYPE 
--		SYNTAX      INTEGER {
--				   valid(1),
--				   invalid(2)
--				  }
--		MAX-ACCESS  read-only 
--		STATUS      current 
--		DESCRIPTION 
--			"Specifies the validity of the entry."
--		::= { mirrorCtrlEntry 4 }
	   
		   
	phyInfTable OBJECT-TYPE 
		SYNTAX      SEQUENCE OF PhyInfEntry
		MAX-ACCESS  not-accessible 
		STATUS      current 
		DESCRIPTION 
			"A table to control the port specific parameters of the device like speed, duplex mode, etc."
		::= { sysPhyInf 1 }
	   
	phyInfEntry OBJECT-TYPE 
		SYNTAX      PhyInfEntry
		MAX-ACCESS  not-accessible 
		STATUS      current 
		DESCRIPTION 
			"An entry appears in this table for each interface in the system.
			Index to the table is the interface index of the port."
		INDEX { phyInfIndex, phyInfMediaType }
		::= { phyInfTable 1 }
			   
	PhyInfEntry ::= SEQUENCE 
	{ 
		phyInfIndex				Integer32,
		phyInfMediaType			INTEGER,
		phyInfLinkStatus    	INTEGER,
		phyInfMode				INTEGER,
		phyInfDuplex			INTEGER,
		phyInfSpeed				INTEGER,
		phyInfFlowCtrl			INTEGER,
		phyInfFlowCtrlOper		INTEGER,
		phyInfAdminStatus		INTEGER,
		phyInfJumboFrameEnable	INTEGER, 
		phyInfEAPPassThrough	INTEGER, 
		phyInfBPDUPassThrough	INTEGER,
		phyInfportSetDescription  DisplayString
	}

	phyInfIndex OBJECT-TYPE 
		SYNTAX      Integer32  (1..28)
		MAX-ACCESS  read-only 
		STATUS      current 
		DESCRIPTION 
			"Interface index of the port for which the configuration
			in this entry applies."
		::= { phyInfEntry 1 }
	
	phyInfMediaType OBJECT-TYPE 
		SYNTAX	INTEGER  {
			copper(1),
			fiber(2)
		}
		MAX-ACCESS  read-only 
		STATUS      current 
		DESCRIPTION 
			"Port media type Copper(1),  Fiber(2)."
	   ::= { phyInfEntry 2 }

	phyInfLinkStatus OBJECT-TYPE
		SYNTAX	INTEGER  {
					up(1),
					down(2)
				}
		MAX-ACCESS        read-only
		STATUS            current
		DESCRIPTION
			"this is the Link Status of port on the web"
		::= { phyInfEntry 3 }
		
	phyInfMode OBJECT-TYPE 
		SYNTAX	INTEGER {
					auto(1),
					noNegotiation(2)
				}
		MAX-ACCESS  read-write 
		STATUS      current 
		DESCRIPTION 
			"Speficies the mode in which the speed, duplex modes and flow control
			of the interface is determined.
 	
			If set as 'auto', the hardware senses speed and negotiates with the port
			on the other end of the link for data transfer operation as
			'full-duplex' or 'half-duplex' and about flow contol.
 	
			If set as 'nonegotiation', the configured values for interface
			speed, duplex mode and flow control will be effective."
		::= { phyInfEntry 4 }

	phyInfDuplex OBJECT-TYPE 
		SYNTAX	INTEGER {
					full(1),
					half(2)
				}
		MAX-ACCESS  read-write 
		STATUS      current 
		DESCRIPTION 
			"Configures interface data transfer mode as full-duplex or half-duplex.
			This object can be configured only if the 'phyInfMode' is 'nonegotiation'.
			If the 'phyInfMode' is 'auto', it obtains the value from Hardware
			after negotiating  with its peer"
		::= { phyInfEntry 5 }

	phyInfSpeed OBJECT-TYPE 
		SYNTAX	INTEGER {
					hundredMBPS(2),
					oneGB(3),
					tenGB(4)
				}
		MAX-ACCESS  read-write 
		STATUS      current 
		DESCRIPTION 
			"Configures interface speed.
			This object can be configured only if the 'phyInfMode' is 'nonegotiation'.
			If the 'phyInfMode' is 'auto', it obtains the value from Hardware
			after negotiating  with its peer
			Note: tenMBPS is not supported in current product"
		::= { phyInfEntry 6 }

	phyInfFlowCtrl OBJECT-TYPE 
		SYNTAX	INTEGER {
					enabled(1),
					disabled(2)
				  }
		MAX-ACCESS  read-write 
		STATUS      current 
		DESCRIPTION 
			"Enables / disables flow control for the interface.
			This object be configured only if the 'phyInfMode' is 'nonegotiation'.
			If the 'phyInfMode' is 'auto', it obtains the value from Hardware 
			after negotiating  with its peer"
		::= { phyInfEntry 7 }
		
	phyInfFlowCtrlOper OBJECT-TYPE 
		SYNTAX	INTEGER {
					enabled(1),
					disabled(2)
				  }
		MAX-ACCESS  read-only 
		STATUS      current 
		DESCRIPTION 
			"Enables / disables flow control for the interface.
			This object be configured only if the 'phyInfMode' is 'nonegotiation'.
			If the 'phyInfMode' is 'auto', it obtains the value from Hardware 
			after negotiating  with its peer"
		::= { phyInfEntry 8}
		
	phyInfAdminStatus OBJECT-TYPE 
		SYNTAX	INTEGER {
					enabled(1),
					disabled(2)
				  }
		MAX-ACCESS  read-write 
		STATUS      current 
		DESCRIPTION 
			"the port configuration status."
	   ::= { phyInfEntry 9 }

	phyInfJumboFrameEnable OBJECT-TYPE 
		SYNTAX	INTEGER {
					enabled(1),
					disabled(2)
				  }
		MAX-ACCESS  read-write 
		STATUS      current 
		DESCRIPTION 
			"Gigabit Web Smart Switches support jumbo frames (frames larger than 
			the Ethernet frame size of 1522 bytes) of up to 10,000 bytes (tagged). 
			Default jumbo frame is disabled."
		::= { phyInfEntry 10 }

	phyInfEAPPassThrough OBJECT-TYPE 
		SYNTAX	INTEGER {
					enabled(1),
					disabled(2)
				 }
		MAX-ACCESS  read-write
		STATUS      current 
		DESCRIPTION 
			"Enables / disables dot1x EAP packet pass through for the interface.
			This object be configured only if the dot1x is disabled."
		::= { phyInfEntry 11 }

	phyInfBPDUPassThrough     OBJECT-TYPE
		SYNTAX	INTEGER  {
					enabled(1),
					disabled(2)
				}
		MAX-ACCESS        read-write
		STATUS            current
		DESCRIPTION
			"Enables / disables STP BPDU passthrough for the interface.
			This object be configured only if the RSTP/MSTP is disabled."
		::= { phyInfEntry 12 }

	phyInfportSetDescription     OBJECT-TYPE
		SYNTAX            DisplayString (SIZE(1..64))
		MAX-ACCESS        read-write
		STATUS            current
		DESCRIPTION
			"Configures port settings Description."
		::= { phyInfEntry 13 }
 
	sysFW              			OBJECT IDENTIFIER ::= { sysTools 1 }
	sysConfig           		OBJECT IDENTIFIER ::= { sysTools 2 }
--	sysCableDiag             	OBJECT IDENTIFIER ::= { sysTools 3 }
--	sysLEDECO             		OBJECT IDENTIFIER ::= { sysTools 4 }
	sysReboot              		OBJECT IDENTIFIER ::= { sysTools 5 }	
	sysPing           			OBJECT IDENTIFIER ::= { sysTools 6 }
	sysEee                      OBJECT IDENTIFIER ::= { sysTools 7 }

	-- Firmware upgrade Operate
	fwDlSrvIpType	OBJECT-TYPE
		SYNTAX		INTEGER{
						ipv4(1),
						ipv6(2)
					}
		MAX-ACCESS  read-write
		STATUS      current
		DESCRIPTION 
			"Address type of IP Address of the remote system to 
			 which the switch file have to be transfer."
		::= { sysFW 1 }

	fwDlSrvIpAddr	OBJECT-TYPE
		SYNTAX InetAddress
		MAX-ACCESS read-write
		STATUS current
		DESCRIPTION
			"The TFTP server's IP address is used to upgrade firmware."
		::= { sysFW 2 }

	fwDlSrvInterfaceName OBJECT-TYPE
		SYNTAX      OCTET STRING (SIZE(1..32))
		MAX-ACCESS  read-only
		STATUS      current
		DESCRIPTION
			   "Specifies the interface name when the fwDlSrvIpAddr is linklocal address."
		   ::= { sysFW 3 } 
			   
	fwDlFileName OBJECT-TYPE
		SYNTAX DisplayString (SIZE(1..128))
		MAX-ACCESS read-write
		STATUS current
		DESCRIPTION
			"Filename in Tftp server directory when Firmware upgrade."
		::= { sysFW 4 }

	fwDlOper	OBJECT-TYPE
		SYNTAX	INTEGER {
					enabled(1)
				}
		 MAX-ACCESS read-write
		 STATUS current
		 DESCRIPTION
			 "upgrade firmware file."
		 ::= { sysFW 5 }

	fwDlOperStatus OBJECT-TYPE
		 SYNTAX INTEGER {
				none(0),
				success(1),
				fail(2),
				progressing(3),
				transmit(4),
				programming(5)
		 }
		 MAX-ACCESS read-only
		 STATUS current
		 DESCRIPTION
			 "The tftp or http operation status when firmware upgrade."
		 ::= { sysFW 6 }
	 
	fwDlProcessPercentage OBJECT-TYPE
		SYNTAX INTEGER(0..100)
		MAX-ACCESS read-only
		STATUS current
		DESCRIPTION
			"The firmware processing percentage represent firmware upgrade process progress."
		::= { sysFW 7 }
		
	fwRetryCount OBJECT-TYPE
		SYNTAX      Integer32 (1..20)
		MAX-ACCESS  read-write
		STATUS      current
		DESCRIPTION
			"The number of retry when upgrade fail."
		::= { sysFW 8 }	
		
	-- Configuration Backup/Restore Operate
	configSrvIpType    OBJECT-TYPE
		SYNTAX	INTEGER {
					ipv4(1),
					ipv6(2)
				}
		MAX-ACCESS  read-write
		STATUS      current
		DESCRIPTION 
			"The TFTP server's IP type is used to backup/restore configuration."
		DEFVAL { ipv4 }
		::= { sysConfig 1 }
		
	configSrvIpAddr OBJECT-TYPE
		SYNTAX	InetAddress
		MAX-ACCESS read-write
		STATUS current
		DESCRIPTION
			"The TFTP server's IP address is used to backup/restore configuration."
		::= { sysConfig 2 }
		
	configSrvInterfaceName OBJECT-TYPE
		SYNTAX      OCTET STRING (SIZE(1..32))
		MAX-ACCESS  read-only
		STATUS      current
		DESCRIPTION
			"Specifies the interface name when the configSrvIpAddr is linklocal address."
		   ::= { sysConfig 3 } 
		   
	configFileName OBJECT-TYPE
		SYNTAX	DisplayString (SIZE(1..128))
		MAX-ACCESS read-write
		STATUS current
		DESCRIPTION
			"Filename in Tftp server directory when configuration backup/restore."
		::= { sysConfig 4 }

	configOper OBJECT-TYPE
		 SYNTAX INTEGER {
				none(0),
				restore(1),
				backup(2),
				save(3)
		 }
		 MAX-ACCESS read-write
		 STATUS current
		 DESCRIPTION
			 "Tell system the type of operation, backup/restore/save configuration file."
		 ::= { sysConfig 5 }

	configOperStatus OBJECT-TYPE
		SYNTAX	INTEGER {
					none(0),
					success(1),
					fail(2),
					progressing(3),
					transmit(4)
				}
		MAX-ACCESS read-only
		STATUS current
		DESCRIPTION
			"The operation status when configuration backup/restore/save."
		::= { sysConfig 6 }

	-- Led ECO mode
	--ledECOModeStatus OBJECT-TYPE
		--SYNTAX	INTEGER {
			--		enabled(1),
			--		disabled(2)
            --   }
		--MAX-ACCESS  read-write
		--STATUS      current
		--DESCRIPTION
		--	"Enables/Disables the LED ECO mode in the system."
		--DEFVAL { enabled }
		--::= { sysLEDECO 1 }

	--ledStatus OBJECT-TYPE
	--	SYNTAX	INTEGER {
	--				on(1),
	--				off(2)
     --          }
	--	MAX-ACCESS  read-only
	--	STATUS      current
	--	DESCRIPTION
	--		"The Led status."
	--	DEFVAL { on }
	--	::= { sysLEDECO 2 }



	rebRestart OBJECT-TYPE
		SYNTAX	INTEGER {
					normal(1),
					reset(2),
					resetwithoutip(3)
				}
		MAX-ACCESS  read-write
		STATUS      current
		DESCRIPTION
			"the object is used to restart the system with the different type."
		DEFVAL { normal }
		::= { sysReboot 1 }
		

	-- ping test module
	pingDestIpType OBJECT-TYPE
		SYNTAX	INTEGER{
					ipv4(1),
					ipv6(2)
				}
		MAX-ACCESS  read-write
		STATUS      current
		DESCRIPTION
			"The IP address type of the node to be pinged."
		DEFVAL { 1 }
		::= { sysPing 1 }

	pingDestIpAddr OBJECT-TYPE
		SYNTAX	InetAddress
		MAX-ACCESS  read-write	
		STATUS      current
		DESCRIPTION
			"The IP address of the node to be pinged,  set ip type before set it."
		::= { sysPing 2 }
		
	pingInterfaceName OBJECT-TYPE
		SYNTAX      OCTET STRING (SIZE(1..32))
		MAX-ACCESS  read-only
		STATUS      current
		DESCRIPTION
			"Specifies the interface name when the pingDestIpAddr is linklocal address."
		::= { sysPing 3 }
		   
	pingTimeout	    OBJECT-TYPE
		SYNTAX      Integer32 (1..5)
		MAX-ACCESS  read-write
		STATUS      current
		DESCRIPTION
			"The time in seconds after which the entity waiting
			for the ping response times out."
		DEFVAL { 3 }
		::= { sysPing 4 }
	
	pingTimes OBJECT-TYPE
		SYNTAX      Integer32 (1..10)
		MAX-ACCESS  read-write	
		STATUS      current
		DESCRIPTION
			"The number of times the given node address is to be pinged."
		DEFVAL { 10 }
		::= { sysPing 5 }

	pingStart OBJECT-TYPE
		SYNTAX      INTEGER { enabled(1), disabled(2) }
		MAX-ACCESS  read-write
		STATUS      current
		DESCRIPTION
			"The ping event of ping operate."
		DEFVAL  { disabled }
		::= { sysPing 6 }

	pingStatus OBJECT-TYPE
		SYNTAX	INTEGER {
					notinitiated (1),
					progress  (2),
					completed (3)
				}
		MAX-ACCESS  read-only
		STATUS      current
		DESCRIPTION
			"The current status of the Ping operate"
		::= { sysPing 7 }

	pingAverageTime	  OBJECT-TYPE
		SYNTAX      Integer32 (0..2147483647)
		MAX-ACCESS  read-only
		STATUS      current
		DESCRIPTION
			"The average value of the round trip time in milli seconds
			to this destination."
		::= { sysPing 8 }

	pingSuccesses OBJECT-TYPE
		SYNTAX      Counter32
		MAX-ACCESS  read-only
		STATUS      current
		DESCRIPTION
			"The number of ping responses received."
		::= { sysPing 9 }

	eeeStatus OBJECT-TYPE
		SYNTAX      INTEGER { enabled(1), disabled(2) }
		MAX-ACCESS read-write
		STATUS current
		DESCRIPTION
			"Enable or disable EEE function."
		DEFVAL  { disabled }
		::= { sysEee 1 }
	

	-- -------------------------------------------------------------
	-- statistics Function
	-- ------------------------------------------------------------- 
	
	-- -------------------------------------------------------------
    -- statistics chart group
    -- -------------------------------------------------------------
	statisticsChartTable  OBJECT-TYPE
		SYNTAX     SEQUENCE OF StatisticsChartEntry
        MAX-ACCESS not-accessible
        STATUS     current
        DESCRIPTION
			"A list of interface entries."
		::= { sysStatistics 1 }		

	statisticsChartEntry OBJECT-TYPE
        SYNTAX     StatisticsChartEntry
        MAX-ACCESS not-accessible
        STATUS     current
        DESCRIPTION
              "An entry containing management information applicable
               to a particular interface"
        INDEX { statisIndex }
        ::= { statisticsChartTable 1 }

	StatisticsChartEntry ::=
            SEQUENCE {
              statisIndex                		InterfaceIndex,              
              statisInOctets                   	Counter32,
			  statisInUcastPkts             	Counter32,
			  statisInNUcastPkts           		Counter32,
			  statisInDiscards    				Counter32,			  
			  statisInErrors                	Counter32,              
			  statisOutOctets             		Counter32,
			  statisOutUcastPkts           		Counter32,
			  statisOutNUcastPkts    			Counter32,			  
			  statisOutDiscards                	Counter32,              
              statisOutErrors                   Counter32,
			  statisEtherDropEvents             Counter32,
			  statisEtherCRCAlignErrors         Counter32,
			  statisEtherUndersizePkts   		Counter32,			  
			  statisEtherOversizePkts           Counter32,              
              statisEtherFragments              Counter32,
			  statisEtherCollisions           	Counter32
            }	
			
	statisIndex OBJECT-TYPE
       SYNTAX      InterfaceIndex
       MAX-ACCESS  read-only
       STATUS      current
       DESCRIPTION
               "A unique value, greater than zero, for each
               interface.  It is recommended that values are assigned
               contiguously starting from 1.  The value for each
               interface sub-layer must remain constant at least from
               one re-initialization of the entity's network
               management system to the next re-initialization."
       ::= { statisticsChartEntry 1 }   

	statisInOctets OBJECT-TYPE
       SYNTAX      Counter32
       MAX-ACCESS  read-only
       STATUS      current
       DESCRIPTION
               "The total number of octets received on the interface,
               including framing characters.
               Discontinuities in the value of this counter can occur
               at re-initialization of the management system."
       ::= { statisticsChartEntry 2 }

	statisInUcastPkts OBJECT-TYPE
       SYNTAX      Counter32
       MAX-ACCESS  read-only
       STATUS      current
       DESCRIPTION
               "The number of packets, delivered by this sub-layer to
               a higher (sub-)layer, which were not addressed to a
               multicast or broadcast address at this sub-layer.

               Discontinuities in the value of this counter can occur
               at re-initialization of the management system."
       ::= { statisticsChartEntry 3 }

	statisInNUcastPkts OBJECT-TYPE
       SYNTAX      Counter32
       MAX-ACCESS  read-only
       STATUS      deprecated
       DESCRIPTION
               "The number of packets, delivered by this sub-layer to
               a higher (sub-)layer, which were addressed to a
               multicast or broadcast address at this sub-layer.

               Discontinuities in the value of this counter can occur
               at re-initialization of the management system."
       ::= { statisticsChartEntry 4 }

	statisInDiscards OBJECT-TYPE
       SYNTAX      Counter32
       MAX-ACCESS  read-only
       STATUS      current
       DESCRIPTION
               "The number of inbound packets which were chosen to be
               discarded even though no errors had been detected to
               prevent their being deliverable to a higher-layer
               protocol.  One possible reason for discarding such a
               packet could be to free up buffer space.

               Discontinuities in the value of this counter can occur
               at re-initialization of the management system."
       ::= { statisticsChartEntry 5 }

	statisInErrors OBJECT-TYPE
       SYNTAX      Counter32
       MAX-ACCESS  read-only
       STATUS      current
       DESCRIPTION
               "For packet-oriented interfaces, the number of inbound
               packets that contained errors preventing them from
               being deliverable to a higher-layer protocol.  For
               character-oriented or fixed-length interfaces, the
               number of inbound transmission units that contained
               errors preventing them from being deliverable to a
               higher-layer protocol.

               Discontinuities in the value of this counter can occur
               at re-initialization of the management system."
       ::= { statisticsChartEntry 6 }

	statisOutOctets OBJECT-TYPE
       SYNTAX      Counter32
       MAX-ACCESS  read-only
       STATUS      current
       DESCRIPTION
               "The total number of octets transmitted out of the
               interface, including framing characters.
               Discontinuities in the value of this counter can occur
               at re-initialization of the management system."
       ::= { statisticsChartEntry 7 }

   statisOutUcastPkts OBJECT-TYPE
       SYNTAX      Counter32
       MAX-ACCESS  read-only
       STATUS      current
       DESCRIPTION
               "The total number of packets that higher-level
               protocols requested be transmitted, and which were not
               addressed to a multicast or broadcast address at this
               sub-layer, including those that were discarded or not
               sent.
               Discontinuities in the value of this counter can occur
               at re-initialization of the management system."
       ::= { statisticsChartEntry 8 }

	statisOutNUcastPkts OBJECT-TYPE
       SYNTAX      Counter32
       MAX-ACCESS  read-only
       STATUS      deprecated
       DESCRIPTION
               "The total number of packets that higher-level
               protocols requested be transmitted, and which were
               addressed to a multicast or broadcast address at this
               sub-layer, including those that were discarded or not
               sent.

               Discontinuities in the value of this counter can occur
               at re-initialization of the management system."
       ::= { statisticsChartEntry 9}

	statisOutDiscards OBJECT-TYPE
       SYNTAX      Counter32
       MAX-ACCESS  read-only
       STATUS      current
       DESCRIPTION
               "The number of outbound packets which were chosen to
               be discarded even though no errors had been detected
               to prevent their being transmitted.  One possible
               reason for discarding such a packet could be to free
               up buffer space.

               Discontinuities in the value of this counter can occur
               at re-initialization of the management system."
       ::= { statisticsChartEntry 10 }

	statisOutErrors OBJECT-TYPE
       SYNTAX      Counter32
       MAX-ACCESS  read-only
       STATUS      current
       DESCRIPTION
               "For packet-oriented interfaces, the number of
               outbound packets that could not be transmitted because
               of errors.  For character-oriented or fixed-length
               interfaces, the number of outbound transmission units
               that could not be transmitted because of errors.

               Discontinuities in the value of this counter can occur
               at re-initialization of the management system."
       ::= { statisticsChartEntry 11 }
	   
	statisEtherDropEvents OBJECT-TYPE
     SYNTAX     Counter32
     MAX-ACCESS read-only
     STATUS     current
     DESCRIPTION
         "The total number of events in which packets
         were dropped by the probe due to lack of resources.
         Note that this number is not necessarily the number of
         packets dropped; it is just the number of times this
         condition has been detected."
     ::= { statisticsChartEntry 12 }
	
	statisEtherCRCAlignErrors OBJECT-TYPE
     SYNTAX     Counter32
     UNITS      "Packets"
     MAX-ACCESS read-only
     STATUS     current
     DESCRIPTION
         "The total number of packets received that
         had a length (excluding framing bits, but
         including FCS octets) of between 64 and 1518
         octets, inclusive, but had either a bad
         Frame Check Sequence (FCS) with an integral
         number of octets (FCS Error) or a bad FCS with
         a non-integral number of octets (Alignment Error)."
     ::= { statisticsChartEntry 13 }
	 
	statisEtherUndersizePkts OBJECT-TYPE
     SYNTAX     Counter32
     UNITS      "Packets"
     MAX-ACCESS read-only
     STATUS     current
     DESCRIPTION
         "The total number of packets received that were
         less than 64 octets long (excluding framing bits,
         but including FCS octets) and were otherwise well
         formed."
     ::= { statisticsChartEntry 14 }
	 
	statisEtherOversizePkts OBJECT-TYPE
     SYNTAX     Counter32
     UNITS      "Packets"
     MAX-ACCESS read-only
     STATUS     current
     DESCRIPTION
         "The total number of packets received that were
         longer than 1518 octets (excluding framing bits,
         but including FCS octets) and were otherwise
         well formed."
     ::= { statisticsChartEntry 15 }
	 
	statisEtherFragments OBJECT-TYPE
     SYNTAX     Counter32
     UNITS      "Packets"
     MAX-ACCESS read-only
     STATUS     current
     DESCRIPTION
         "The total number of packets received that were less than
         64 octets in length (excluding framing bits but including
         FCS octets) and had either a bad Frame Check Sequence
         (FCS) with an integral number of octets (FCS Error) or a
         bad FCS with a non-integral number of octets (Alignment
         Error).

         Note that it is entirely normal for statisEtherFragments to
         increment.  This is because it counts both runts (which are
         normal occurrences due to collisions) and noise hits."
     ::= { statisticsChartEntry 16 }
	
	statisEtherCollisions OBJECT-TYPE
     SYNTAX     Counter32
     UNITS      "Collisions"
     MAX-ACCESS read-only
     STATUS     current
     DESCRIPTION
         "The best estimate of the total number of collisions
         on this Ethernet segment.

         The value returned will depend on the location of the
         RMON probe. Section 8.2.1.3 (10BASE-5) and section
         10.3.1.3 (10BASE-2) of IEEE standard 802.3 states that a
         station must detect a collision, in the receive mode, if
         three or more stations are transmitting simultaneously.  A
         repeater port must detect a collision when two or more

         stations are transmitting simultaneously.  Thus a probe
         placed on a repeater port could record more collisions
         than a probe connected to a station on the same segment
         would.

         Probe location plays a much smaller role when considering
         10BASE-T.  14.2.1.4 (10BASE-T) of IEEE standard 802.3
         defines a collision as the simultaneous presence of signals
         on the DO and RD circuits (transmitting and receiving
         at the same time).  A 10BASE-T station can only detect
         collisions when it is transmitting.  Thus probes placed on
         a station and a repeater, should report the same number of
         collisions.

         Note also that an RMON probe inside a repeater should
         ideally report collisions between the repeater and one or
         more other hosts (transmit collisions as defined by IEEE
         802.3k) plus receiver collisions observed on any coax
         segments to which the repeater is connected."
     ::= { statisticsChartEntry 17 }

----------------------------------------------------------------------------------------------
	-- the Interfaces table

	statisticsClearTable OBJECT-TYPE
		SYNTAX      SEQUENCE OF StatisticsClearEntry
		MAX-ACCESS  not-accessible
		STATUS      current
		DESCRIPTION
				"A list of interface entries.  The number of entries is
				given by the value of ifNumber."
		::= { sysStatistics 2 }

	statisticsClearEntry OBJECT-TYPE
		SYNTAX      StatisticsClearEntry
		MAX-ACCESS  not-accessible
		STATUS      current
		DESCRIPTION
				"An entry containing management information applicable to a
				particular interface."
		INDEX   { statisticsClearIndex }
		::= { statisticsClearTable 1 }

	StatisticsClearEntry ::=
		SEQUENCE {
			statisticsClearIndex            INTEGER,
			statisticsClearStatus			INTEGER
		}

	statisticsClearIndex OBJECT-TYPE
		SYNTAX      INTEGER   (1..28)
		MAX-ACCESS  read-only
		STATUS      current
		DESCRIPTION
				"A unique value, greater than zero, for each interface.  It
				is recommended that values are assigned contiguously
				starting from 1.  The value for each interface sub-layer
				must remain constant at least from one re-initialization of
				the entity's network management system to the next re-
				initialization."
		::= { statisticsClearEntry 1 }

	statisticsClearStatus OBJECT-TYPE
	   SYNTAX      INTEGER { enabled(1), disabled(2) }
	   MAX-ACCESS  read-write
	   STATUS      current
	   DESCRIPTION
			   "Enable or disable MAC Counters Clear on read by port."
	   ::= { statisticsClearEntry 2 }
		 
-- ------------------------------------------------------------------
-- The smart fan Setting
-- ------------------------------------------------------------------
-- fan group	
	smartFanGlobal                 OBJECT IDENTIFIER ::= { sysSmartFan 1 }
--	smartFanTraps                  OBJECT IDENTIFIER ::= { sysSmartFan 2 }
-- fan group end
    smartFanStatus OBJECT-TYPE 
			SYNTAX      INTEGER {
					ok(0),
					fail(1)
					}
			MAX-ACCESS  read-only 
			STATUS      current 
			DESCRIPTION 
					"Show smartfan status.
					Smartfan status will show if the fan is run ok or run fail ,if the status is fail ,
					it means some error happened on the smartfan "
			DEFVAL  { ok }
			::= { smartFanGlobal 1 }
			
    smartFanThermalSensorStatus OBJECT-TYPE 
			SYNTAX      INTEGER {
					low(0),
					high(1)
					}
			MAX-ACCESS  read-only 
			STATUS      current 
			DESCRIPTION 
					"The temperature will be update per-minute, it shows the Thermalsenor's status at real-time "
			DEFVAL  { low }
			::= { smartFanGlobal 3 }

--smart fan snmp traps definition here 
--    smartFanTrapList           	OBJECT IDENTIFIER ::= { smartFanTraps 0 }
	
-- 	smartFanHighTemperature NOTIFICATION-TYPE
--      STATUS             current
--      DESCRIPTION
--       "This is a trap that will send to snmp manager,and it will be generated when side fan is in high temperature."
-- 	::= {smartFanTrapList 1 }
	
--	smartFanLowTemperature NOTIFICATION-TYPE
--      STATUS             current
--      DESCRIPTION
--       "This is a trap that will send to snmp manager,and it will be generated when side fan is in low temperature."
-- 	::= {smartFanTrapList 2 }
	
--  	smartFanFailed NOTIFICATION-TYPE
--      STATUS             current
--      DESCRIPTION
--       "This is a trap that will send to snmp manager,and it will be generated when side fan failed."
-- 	::= {smartFanTrapList 3 }		  


-- ----------------------------------------------------------------
-- The STATIC Multicast MAC group
-- ----------------------------------------------------------------
sysStaticMcast    			OBJECT IDENTIFIER ::= { sysMulticast 1 }

staicMcastTable OBJECT-TYPE
	SYNTAX SEQUENCE OF StaticMcastEntry
	MAX-ACCESS not-accessible
	STATUS current
	DESCRIPTION
		"A list of the Static Multicast MACs"
	::= { sysStaticMcast 1 }

staicMcastEntry OBJECT-TYPE
	SYNTAX StaticMcastEntry
	MAX-ACCESS not-accessible
	STATUS current
	DESCRIPTION
		"A Static Multicast MAC entry containing the mac and forwarding port."
--	INDEX {staticMcastVlanId, staticMcastVlanType, staticMcastMac}
	INDEX {staticMcastVlanId, staticMcastMac}
	::= { staicMcastTable 1 }

StaticMcastEntry ::= SEQUENCE {
	staticMcastVlanId     	INTEGER,
--	staticMcastVlanType		INTEGER,
	staticMcastMac          MacAddress,
	staticMcastPortList		PortList,
	staticMcastRowStatus	RowStatus
}

staticMcastVlanId OBJECT-TYPE
	SYNTAX INTEGER  (1..4094)
	MAX-ACCESS read-only
	STATUS current
	DESCRIPTION
		"The VLAN ID of the Static Multicast MAC entry."
	::= { staicMcastEntry 1 }

--staticMcastVlanType OBJECT-TYPE
--	SYNTAX      INTEGER  { portBased(1), dot1q(2) } 
--	MAX-ACCESS  read-only 
--	STATUS      current 
--	DESCRIPTION 
--		"VALN type include port-based VLAN and 802.1Q VLAN."
--	::= { staicMcastEntry 2 } 	
	
staticMcastMac OBJECT-TYPE
   SYNTAX MacAddress
   MAX-ACCESS read-only
   STATUS current
   DESCRIPTION
	   "The MAC address associated of the Static Multicast MAC entry."
   ::= { staicMcastEntry 3 }

staticMcastPortList OBJECT-TYPE
	SYNTAX      PortList
	MAX-ACCESS  read-write
	STATUS      current
	DESCRIPTION
	   "List of ports onto which the multicast data
		packets destined for this group will be forwarded."
	::= { staicMcastEntry 4 }

staticMcastRowStatus OBJECT-TYPE
	SYNTAX     RowStatus
	MAX-ACCESS read-write
	STATUS     current
	DESCRIPTION
		"The status of an entry in the Static Multicast MAC Table.  Only a subset
		 of the rowstatus variables (active, createAndGo, destroy) 
		 are available. The trunk member port can not set up Static Multicast MAC."
	::= { staicMcastEntry 5 }
     
       -- ----------------------------------------------------------------
       -- The vlan group
       -- ---------------------------------------------------------------- 
	   	vlanGlobal 			OBJECT IDENTIFIER ::= { sysVLAN 1 }
		vlanDot1QVLAN		OBJECT IDENTIFIER ::= { sysVLAN 3 }
       -- --------------------------------------------------------------
       -- Dot1q VLAN Gloabal info.
       -- --------------------------------------------------------------
       vlanFwdTabMode OBJECT-TYPE
            SYNTAX INTEGER {
                   ivl(1),
                   svl(2)
            }
            MAX-ACCESS read-write
            STATUS current
            DESCRIPTION
                "Dot1q VLAN Forwarding Table mode"
            ::= { vlanGlobal  1}
	   -- -------------------------------------------------------------
       -- The static vlan table
       -- -------------------------------------------------------------  
       
		dot1qVlanStaticTable OBJECT-TYPE
	    SYNTAX      SEQUENCE OF Dot1qVlanStaticEntry
	    MAX-ACCESS  not-accessible
	    STATUS      current
	    DESCRIPTION
	        "A table containing static configuration information for
	        each VLAN configured into the device by (local or
	        network) management.  All entries are permanent and will
	        be restored after the device is reset."
	    ::= { vlanDot1QVLAN 1 }
	
		dot1qVlanStaticEntry OBJECT-TYPE
	    SYNTAX      Dot1qVlanStaticEntry
	    MAX-ACCESS  not-accessible
	    STATUS      current
	    DESCRIPTION
	        "Static information for a VLAN configured into the
	        device by (local or network) management."
	    INDEX   { dot1qVlanStaticVlanId }
	    ::= { dot1qVlanStaticTable 1 }
	
		Dot1qVlanStaticEntry ::=
	    SEQUENCE {
			dot1qVlanStaticVlanId
				VlanId,
	        dot1qVlanStaticName
	            SnmpAdminString,
	        dot1qVlanStaticEgressPorts
	            PortList,
	        dot1qVlanStaticUntaggedPorts
	            PortList,
	        dot1qVlanStaticRowStatus
	            RowStatus
	    }
		
		dot1qVlanStaticVlanId OBJECT-TYPE
		SYNTAX      VlanId
		MAX-ACCESS  read-only
		STATUS      current
		DESCRIPTION
			"The VLAN-ID or other identifier referring to this VLAN."
		::= { dot1qVlanStaticEntry 1 }
		
		dot1qVlanStaticName OBJECT-TYPE
	    SYNTAX      SnmpAdminString (SIZE (0..32))
	    MAX-ACCESS  read-create
	    STATUS      current
	    DESCRIPTION
	        "An administratively assigned string, which may be used
	        to identify the VLAN."
	    REFERENCE
	        "IEEE 802.1Q/D11 Section 12.10.2.1"
	    ::= { dot1qVlanStaticEntry 2 }
		   
		dot1qVlanStaticEgressPorts OBJECT-TYPE
	    SYNTAX      PortList
	    MAX-ACCESS  read-create
	    STATUS      current
	    DESCRIPTION
	        "The set of ports which are permanently assigned to the
	        egress list for this VLAN by management.  Changes to a
	        bit in this object affect the per-port per-VLAN
	        Registrar control for Registration Fixed for the
	        relevant GVRP state machine on each port.  A port may
	        not be added in this set if it is already a member of
	        the set of ports in dot1qVlanForbiddenEgressPorts.  The
	        default value of this object is a string of zeros of
	        appropriate length, indicating not fixed."
	    REFERENCE
	        "IEEE 802.1Q/D11 Section 12.7.7.3, 11.2.3.2.3"
	    ::= { dot1qVlanStaticEntry 3 }	
		
		dot1qVlanStaticUntaggedPorts OBJECT-TYPE
	    SYNTAX      PortList
	    MAX-ACCESS  read-create
	    STATUS      current
	    DESCRIPTION
	        "The set of ports which should transmit egress packets
	        for this VLAN as untagged.  The default value of this
	        object for the default VLAN (dot1qVlanIndex = 1) is a string
	        of appropriate length including all ports.  There is no
	        specified default for other VLANs.  If a device agent cannot
	        support the set of ports being set then it will reject the
	        set operation with an error. An example might be if a
	        manager attempts to set more than one VLAN to be untagged
	        on egress where the device does not support this IEEE 802.1Q
	        option."
	    REFERENCE
	        "IEEE 802.1Q/D11 Section 12.10.2.1"
	    ::= { dot1qVlanStaticEntry 4 }
	
		dot1qVlanStaticRowStatus OBJECT-TYPE
	    SYNTAX      RowStatus
	    MAX-ACCESS  read-create
	    STATUS      current
	    DESCRIPTION
	        "This object indicates the status of this entry."
	    ::= { dot1qVlanStaticEntry 5 }
		
	-- -------------------------------------------------------------
	-- The Management VLAN Configuration Table
	-- -------------------------------------------------------------
		dot1qMgmtVlanTable OBJECT-TYPE
	    SYNTAX      SEQUENCE OF Dot1qMgmtVlanEntry
	    MAX-ACCESS  not-accessible
	    STATUS      current
	    DESCRIPTION
	        "A table containing static configuration information for
	        each VLAN configured into the device by (local or
	        network) management.  All entries are permanent and will
	        be restored after the device is reset."
	    ::= { vlanDot1QVLAN 2 }
	
		dot1qMgmtVlanEntry OBJECT-TYPE
	    SYNTAX      Dot1qMgmtVlanEntry
	    MAX-ACCESS  not-accessible
	    STATUS      current
	    DESCRIPTION
	        "Static information for a VLAN configured into the
	        device by (local or network) management."
	    INDEX   { dot1qMgmtVlanId }
	    ::= { dot1qMgmtVlanTable 1 }
	
		Dot1qMgmtVlanEntry ::=
	    SEQUENCE {
			 dot1qMgmtVlanId
				VlanId,
	         dot1qMgmtVlanStatus
	         	INTEGER
	    }
		
		dot1qMgmtVlanId OBJECT-TYPE
		SYNTAX      VlanId
		MAX-ACCESS  read-only
		STATUS      current
		DESCRIPTION
			"The VLAN-ID or other identifier referring to this VLAN."
		::= { dot1qMgmtVlanEntry 1 }
		
		dot1qMgmtVlanStatus OBJECT-TYPE
		SYNTAX      INTEGER {
						  enabled      (1),
						  disabled	   (2)
				    } 
	   MAX-ACCESS  read-create
	   STATUS      current
	   DESCRIPTION
		"Current VLAN is Management VLAN or not."
	   ::= { dot1qMgmtVlanEntry 2 }
	   
	-- -------------------------------------------------------------
	-- The VLAN Port Configuration Table
	-- -------------------------------------------------------------
	
		dot1qPortVlanTable OBJECT-TYPE
	    SYNTAX      SEQUENCE OF Dot1qPortVlanEntry
	    MAX-ACCESS  not-accessible
	    STATUS      current
	    DESCRIPTION
	        "A table containing per port control and status
	        information for VLAN configuration in the device."
	    ::= { vlanDot1QVLAN 3 }
	
		dot1qPortVlanEntry OBJECT-TYPE
	    SYNTAX      Dot1qPortVlanEntry
	    MAX-ACCESS  not-accessible
	    STATUS      current
	    DESCRIPTION
	        "Information controlling VLAN configuration for a port
	        on the device.  This is indexed by dot1dBasePort."
	    INDEX { dot1qPortIndex }
	    ::= { dot1qPortVlanTable 1 }
	
		Dot1qPortVlanEntry ::=
	    SEQUENCE {
			dot1qPortIndex
			Integer32,
	        dot1qPvid
	        VlanIndex,
			dot1qPortAcceptableFrameTypes
            INTEGER,
			dot1qPortIngressFiltering
            TruthValue
	        	 }
	
	dot1qPortIndex OBJECT-TYPE
       SYNTAX      Integer32 (1..65535)
       MAX-ACCESS  read-only
       STATUS      current
       DESCRIPTION
           "The port number of the port for which this entry
           contains bridge management information."
       ::= { dot1qPortVlanEntry 1 }
	   
		dot1qPvid OBJECT-TYPE
	    SYNTAX      VlanIndex
	    MAX-ACCESS  read-write
	    STATUS      current
	    DESCRIPTION
	        "The PVID, the VLAN ID assigned to untagged frames or
	        Priority-Tagged frames received on this port."
	    REFERENCE
	        "IEEE 802.1Q/D11 Section 12.10.1.1"
	    DEFVAL      { 1 }
	    ::= { dot1qPortVlanEntry 2 }     
	
		dot1qPortAcceptableFrameTypes OBJECT-TYPE
		SYNTAX      INTEGER {
						admitAll(1),
						admitOnlyVlanTagged(2),
						admitOnlyUntaggedAndPriorityTagged(3) 
					}
		MAX-ACCESS  read-write
		STATUS      current
		DESCRIPTION
			"When this is admitOnlyVlanTagged(2) the device will
			discard untagged frames or Priority-Tagged frames
			received on this port.  When admitAll(1), untagged
			frames or Priority-Tagged frames received on this port
			will be accepted and assigned to the PVID for this port.

			This control does not affect VLAN independent BPDU
			frames, such as GVRP and STP.  It does affect VLAN
			dependent BPDU frames, such as GMRP."
		REFERENCE
			"IEEE 802.1Q/D11 Section 12.10.1.3"
		DEFVAL      { admitAll }
		::= { dot1qPortVlanEntry 3 }

		dot1qPortIngressFiltering OBJECT-TYPE
		SYNTAX      TruthValue
		MAX-ACCESS  read-write
		STATUS      current
		DESCRIPTION
			"When this is true(1) the device will discard incoming
			frames for VLANs which do not include this Port in its
			Member set.  When false(2), the port will accept all
			incoming frames.

			This control does not affect VLAN independent BPDU
			frames, such as GVRP and STP.  It does affect VLAN
			dependent BPDU frames, such as GMRP."
		REFERENCE
			"IEEE 802.1Q/D11 Section 12.10.1.4"
		DEFVAL      { true }
		::= { dot1qPortVlanEntry 4 }
	
	-- -------------------------------------------------------------
	-- The VLAN Current VLAN Table including static and GVRP learnt
	-- -------------------------------------------------------------
	
		dot1qVlanCurrentTable OBJECT-TYPE
		SYNTAX      SEQUENCE OF Dot1qVlanCurrentEntry
		MAX-ACCESS  not-accessible
		STATUS      current
		DESCRIPTION
			"A table containing current configuration information
			for each VLAN currently configured into the device by
			(local or network) management, or dynamically created
			as a result of GVRP requests received."
		::= { vlanDot1QVLAN 4 }

		dot1qVlanCurrentEntry OBJECT-TYPE
		SYNTAX      Dot1qVlanCurrentEntry
		MAX-ACCESS  not-accessible
		STATUS      current
		DESCRIPTION
			"Information for a VLAN configured into the device by
			(local or network) management, or dynamically created
			as a result of GVRP requests received."
		INDEX   { dot1qVlanTimeMark,dot1qVlanId }
		::= { dot1qVlanCurrentTable 1 }

		Dot1qVlanCurrentEntry ::=
		SEQUENCE {
			dot1qVlanTimeMark
				TimeFilter,
			dot1qVlanId
				VlanIndex,
			dot1qVlanName
	            SnmpAdminString,
			dot1qVlanFdbId
				Unsigned32,
			dot1qVlanCurrentEgressPorts
				PortList,
			dot1qVlanCurrentUntaggedPorts
				PortList,
			dot1qVlanStatus
				INTEGER	
		}
		
		dot1qVlanTimeMark OBJECT-TYPE
		SYNTAX      TimeFilter
		MAX-ACCESS  read-only
		STATUS      current
		DESCRIPTION
        "A TimeFilter for this entry.  See the TimeFilter
        textual convention to see how this works."
		::= { dot1qVlanCurrentEntry 1 }
	
		dot1qVlanId OBJECT-TYPE
		SYNTAX      VlanIndex
		MAX-ACCESS  read-only
		STATUS      current
		DESCRIPTION
			"The VLAN-ID or other identifier referring to this VLAN."
		::= { dot1qVlanCurrentEntry 2}

		dot1qVlanName OBJECT-TYPE
	    SYNTAX      SnmpAdminString (SIZE (0..32))
	    MAX-ACCESS  read-only
	    STATUS      current
	    DESCRIPTION
	        "An administratively assigned string, which may be used
	        to identify the VLAN."
	    REFERENCE
	        "IEEE 802.1Q/D11 Section 12.10.2.1"
	    ::= { dot1qVlanCurrentEntry 3 }
		
		dot1qVlanFdbId OBJECT-TYPE
		SYNTAX      Unsigned32
		MAX-ACCESS  read-only
		STATUS      current
		DESCRIPTION
			"The Filtering Database used by this VLAN.  This is one
			of the dot1qFdbId values in the dot1qFdbTable.  This
			value is allocated automatically by the device whenever
			the VLAN is created: either dynamically by GVRP, or by
			management, in dot1qVlanStaticTable.  Allocation of this
			value follows the learning constraints defined for this
			VLAN in dot1qLearningConstraintsTable."
		::= { dot1qVlanCurrentEntry 4 }

		dot1qVlanCurrentEgressPorts OBJECT-TYPE
		SYNTAX      PortList
		MAX-ACCESS  read-only
		STATUS      current
		DESCRIPTION
			"The set of ports that are transmitting traffic for
			this VLAN as either tagged or untagged frames."
		REFERENCE
			"IEEE 802.1Q/D11 Section 12.10.2.1"
		::= { dot1qVlanCurrentEntry 5 }

		dot1qVlanCurrentUntaggedPorts OBJECT-TYPE
		SYNTAX      PortList
		MAX-ACCESS  read-only
		STATUS      current
		DESCRIPTION
			"The set of ports that are transmitting traffic for
			this VLAN as untagged frames."
		REFERENCE
			"IEEE 802.1Q/D11 Section 12.10.2.1"
		::= { dot1qVlanCurrentEntry 6 }
		
		dot1qVlanStatus OBJECT-TYPE
		SYNTAX      INTEGER {
                    other(1),
                    permanent(2),
                    dynamicGvrp(3)
                }
		MAX-ACCESS  read-only
		STATUS      current
		DESCRIPTION
        "This object indicates the status of this entry.
            other(1) - this entry is currently in use, but the
                conditions under which it will remain so differ
                from the following values.
            permanent(2) - this entry, corresponding to an entry
                in dot1qVlanStaticTable, is currently in use and
                will remain so after the next reset of the
                device.  The port lists for this entry include
                ports from the equivalent dot1qVlanStaticTable
                entry and ports learned dynamically.
            dynamicGvrp(3) - this entry is currently in use
                and will remain so until removed by GVRP.  There
                is no static entry for this VLAN, and it will be
                removed when the last port leaves the VLAN."
		::= { dot1qVlanCurrentEntry 7 }
		

	sysStaticUnicast   	  OBJECT IDENTIFIER ::= { sysFwdTable 1 } 
	
	-- Static Mac table for 802.1Q VLAN
	staticUnicastTable OBJECT-TYPE
		SYNTAX SEQUENCE OF StaticUnicastEntry
		MAX-ACCESS not-accessible
		STATUS current
		DESCRIPTION
			"A list of the Static MACs"
		::= { sysStaticUnicast 1 }

	staticUnicastEntry OBJECT-TYPE
		SYNTAX StaticUnicastEntry
		MAX-ACCESS not-accessible
		STATUS current
		DESCRIPTION
			"A Static MAC entry containing the mac and forwarding port."

--		INDEX {staticVlanType, staticVlanId, staticMac}
		INDEX {staticVlanId, staticMac}
		::= { staticUnicastTable 1 }

	StaticUnicastEntry ::= SEQUENCE 
	{
--		staticVlanType		INTEGER,
		staticVlanId		Integer32,
		staticMac			MacAddress,
		staticPortAllowed	Integer32,
		staticRowStatus		RowStatus
	}

--	staticVlanType OBJECT-TYPE
--		SYNTAX INTEGER { portBased(1), dot1q(2) }
--		MAX-ACCESS read-only
--		STATUS current
--		DESCRIPTION
--			"The VLAN type of the staticTable MAC entry."
--		DEFVAL { 2 }
--		::= { staticUnicastEntry 1 }

	staticVlanId OBJECT-TYPE
		SYNTAX Integer32 (1..4094)
		MAX-ACCESS read-only
		STATUS current
		DESCRIPTION
			"The VLAN ID of the staticTable MAC entry."
		::= { staticUnicastEntry 2 }

	staticMac OBJECT-TYPE
		SYNTAX MacAddress
		MAX-ACCESS read-only
		STATUS current
		DESCRIPTION
			"The MAC address associated of the staticTable MAC entry.
			When create entry by mib input mac like 
			'0.0.0.17.34.51'(it is decimal mac),
			after create this entry, walk it will show 
			'00:00:00:11:22:33'(it is hexadecimal mac)"
		::= { staticUnicastEntry 3 }

	staticPortAllowed OBJECT-TYPE
		SYNTAX Integer32
		MAX-ACCESS read-create
		STATUS current
		DESCRIPTION
			"The forwarding port of the staticTable MAC entry."
		::= { staticUnicastEntry 4 }
	
	staticRowStatus OBJECT-TYPE
		SYNTAX     RowStatus
		MAX-ACCESS read-create
		STATUS     current
		DESCRIPTION
			"The status of an mac entry."
		::= { staticUnicastEntry 5 }


	sysDynamicFdb   	  OBJECT IDENTIFIER ::= { sysFwdTable 2 } 
	
	-- -------------------------------------------------------------
-- Multiple Forwarding Databases for 802.1Q Transparent devices
-- This table is an alternative to the fsDot1dTpFdbTable,
-- previously defined for 802.1D devices which only support a
-- single Forwarding Database.
-- -------------------------------------------------------------

dynamicFdbTable OBJECT-TYPE
    SYNTAX      SEQUENCE OF DynamicFdbEntry
    MAX-ACCESS  not-accessible
    STATUS      current
    DESCRIPTION
        "A table that contains information about unicast entries
        for which the device has forwarding and/or filtering
        information.  This information is used by the
        transparent bridging function in determining how to
        propagate a received frame. This table maintains context ID
        as one more index to support Multiple Instances."
    REFERENCE
        "IEEE 802.1Q/D11 Section 12.7.7"
    ::= { sysDynamicFdb 1 }

dynamicFdbEntry OBJECT-TYPE
    SYNTAX      DynamicFdbEntry
    MAX-ACCESS  not-accessible
    STATUS      current
    DESCRIPTION
        "Information about a specific unicast MAC address for
        which the device has some forwarding and/or filtering
        information."
    INDEX   { dynamicFdbId, dynamicFdbMacAddr }
    ::= { dynamicFdbTable 1 }

DynamicFdbEntry ::=
    SEQUENCE {
		dynamicFdbId
			Unsigned32,
        dynamicFdbMacAddr
            MacAddress,
        dynamicFdbPort
            DisplayString,
        dynamicFdbStatus
            INTEGER
    }

dynamicFdbId OBJECT-TYPE
    SYNTAX       Unsigned32
    MAX-ACCESS   read-only
    STATUS       current
    DESCRIPTION
        "The identity of this Filtering Database."
    ::= { dynamicFdbEntry 1 }
	
dynamicFdbMacAddr OBJECT-TYPE
    SYNTAX      MacAddress
    MAX-ACCESS  read-only
    STATUS      current
    DESCRIPTION
        "A unicast MAC address for which the device has
        forwarding and/or filtering information."
    ::= { dynamicFdbEntry 2 }

dynamicFdbPort OBJECT-TYPE
    SYNTAX      DisplayString 
    MAX-ACCESS  read-only
    STATUS      current
    DESCRIPTION
        "The port number of the port on
        which a frame having a source address equal to the value
        of the corresponding instance of dynamicFdbMacAddr has
        been seen.If the port is LA port, will show 'po' before port."
    ::= { dynamicFdbEntry 3 }

dynamicFdbStatus OBJECT-TYPE
    SYNTAX      INTEGER {
                    other(1),
                    invalid(2),
                    dynamic(3),
                    self(4),
                    static(5)
                }
    MAX-ACCESS  read-only
    STATUS      current
    DESCRIPTION
        "The status of this entry.  The meanings of the values
        are:
            other(1) - none of the following.  This may include
                the case where some other MIB object (not the
                corresponding instance of dynamicFdbPort, nor an
                entry in the fsDot1qStaticUnicastTable) is being
                used to determine if and how frames addressed to
                the value of the corresponding instance of
                dynamicFdbMacAddr are being forwarded.
            invalid(2) - this entry is no longer valid (e.g., it
                was learned but has since aged out), but has not
                yet been flushed from the table.
            learned(3) - the value of the corresponding instance
                of dynamicFdbPort was learned and is being used.
            self(4) - the value of the corresponding instance of
                dynamicFdbMacAddr represents one of the device's
                addresses.  The corresponding instance of
                dynamicFdbPort indicates which of the device's
                ports has this address.
            static(5) - the value of the corresponding instance of
                dynamicFdbMacAddr is also the value of an
                existing instance of fsDot1qStaticAddress."
    ::= { dynamicFdbEntry 4 }

-- -------------------------------------------------------------



		
-- ----------------------------------------------------------
-- The GVRP Groups
-- ----------------------------------------------------------
	gvrpGlobal 			OBJECT IDENTIFIER ::= { sysGVRP 1 }
    gvrpPortSetting		OBJECT IDENTIFIER ::= { sysGVRP 2 }
    gvrpTimeSetting		OBJECT IDENTIFIER ::= { sysGVRP 3 }
   -- --------------------------------------------------------------
   -- GVRP Gloabal info.
   -- --------------------------------------------------------------
	gvrpStatus OBJECT-TYPE
		SYNTAX      INTEGER { enabled(1), disabled(2) }
		MAX-ACCESS read-write
		STATUS current
		DESCRIPTION
			"Enable/Disable GVRP mechanism."
		DEFVAL  { disabled }
		::= { gvrpGlobal 1 }

   -- --------------------------------------------------------------
   -- GVRP port info.
   -- --------------------------------------------------------------		
	gvrpPortTable OBJECT-TYPE
		SYNTAX      SEQUENCE OF GvrpPortEntry
		MAX-ACCESS  not-accessible
		STATUS      current
		DESCRIPTION
			"A table containing per-port control and status
			information for VLAN configuration in the device."
		::= { gvrpPortSetting 1 }

	gvrpPortEntry OBJECT-TYPE
		SYNTAX      GvrpPortEntry
		MAX-ACCESS  not-accessible
		STATUS      current
		DESCRIPTION
			"Information controlling VLAN configuration for a port
			on the device.  This is indexed by dot1dBasePort."
		INDEX { gvrpPortIndex }
		::= { gvrpPortTable 1 }

	GvrpPortEntry ::=
		SEQUENCE {
			gvrpPortIndex
				Integer32,
			gvrpPortGvrpStatus
				INTEGER,
			gvrpPortRestrictedVlanRegistration
				INTEGER
		}

	gvrpPortIndex OBJECT-TYPE
       SYNTAX      Integer32  (1..28)
       MAX-ACCESS  read-only
       STATUS      current
       DESCRIPTION
           "The port number of the port for which this entry
           contains bridge management information."
       ::= { gvrpPortEntry 1 }
	   
	gvrpPortGvrpStatus OBJECT-TYPE
		SYNTAX      INTEGER { 
						enabled(1), 
						disabled(2)
					}
		MAX-ACCESS  read-write
		STATUS      current
		DESCRIPTION
			"The state of GVRP operation on this port.  The value
			enabled(1) indicates that GVRP is enabled on this port,
			as long as dot1qGvrpStatus is also enabled for this
			device.  When disabled(2) but dot1qGvrpStatus is still
			enabled for the device, GVRP is disabled on this port:
			any GVRP packets received will be silently discarded, and
			no GVRP registrations will be propagated from other
			ports.  This object affects all GVRP Applicant and
			Registrar state machines on this port.  A transition
			from disabled(2) to enabled(1) will cause a reset of all
			GVRP state machines on this port.

			The value of this object MUST be retained across
			reinitializations of the management system."
		DEFVAL      { enabled }
		::= { gvrpPortEntry 2 }

	gvrpPortRestrictedVlanRegistration OBJECT-TYPE
		SYNTAX      INTEGER { 
						enabled(1), 
						disabled(2)
					}
		MAX-ACCESS  read-write
		STATUS      current
		DESCRIPTION
			"The state of Restricted VLAN Registration on this port.
			 If the value of this control is enabled(1), then creation
			 of a new dynamic VLAN entry is permitted only if there
			 is a Static VLAN Registration Entry for the VLAN concerned,
			 in which the Registrar Administrative Control value for
			 this port is Normal Registration.

			The value of this object MUST be retained across
			reinitializations of the management system."
		REFERENCE
			"IEEE 802.1u clause 11.2.3.2.3, 12.10.1.7."
		DEFVAL      { disabled }
		::= { gvrpPortEntry 3 }

   -- --------------------------------------------------------------
   -- GVRP timer info.
   -- --------------------------------------------------------------		
	gvrpTimeTable OBJECT-TYPE
		SYNTAX      SEQUENCE OF GvrpTimeTableEntry
		MAX-ACCESS  not-accessible
		STATUS      current
		DESCRIPTION
			"A table of GARP control information about every bridge
			port.  This is indexed by dot1dBasePort."
		::= { gvrpTimeSetting 1 }

	gvrpTimeTableEntry OBJECT-TYPE
		SYNTAX      GvrpTimeTableEntry
		MAX-ACCESS  not-accessible
		STATUS      current
		DESCRIPTION
			"GARP control information for a bridge port."
		INDEX { gvrpPortNum }
		::= { gvrpTimeTable 1 }

	GvrpTimeTableEntry ::=
		SEQUENCE {
			gvrpPortNum
				Integer32,
			gvrpJoinTime
				TimeInterval,
			gvrpLeaveTime
				TimeInterval,
			gvrpLeaveAllTime
				TimeInterval
		}

	gvrpPortNum OBJECT-TYPE
       SYNTAX      Integer32  (1..28)
       MAX-ACCESS  read-only
       STATUS      current
       DESCRIPTION
           "The port number of the port for which this entry
           contains bridge management information."
       ::= { gvrpTimeTableEntry 1 }
	   
	gvrpJoinTime OBJECT-TYPE
		SYNTAX      TimeInterval (1..1073741810)
		MAX-ACCESS  read-write
		STATUS      current
		DESCRIPTION
			"The GARP Join time, in centiseconds.

			The value of this object MUST be retained across
			reinitializations of the management system."
		DEFVAL      { 200 }
		::= { gvrpTimeTableEntry 2 }

	gvrpLeaveTime OBJECT-TYPE
		SYNTAX      TimeInterval (30..2147483630)
		MAX-ACCESS  read-write
		STATUS      current
		DESCRIPTION
			"The GARP Leave time, in centiseconds.

			The value of this object MUST be retained across
			reinitializations of the management system."
		DEFVAL      { 600 }
		::= { gvrpTimeTableEntry 3 }

	gvrpLeaveAllTime OBJECT-TYPE
		SYNTAX      TimeInterval  (40..2147483640)
		MAX-ACCESS  read-write
		STATUS      current
		DESCRIPTION
			"The GARP LeaveAll time, in centiseconds.

			The value of this object MUST be retained across
			reinitializations of the management system."
		DEFVAL      { 10000 }
		::= { gvrpTimeTableEntry 4 }
	  
--    userAuthenticationmethod  	OBJECT IDENTIFIER ::= { sysAdministration 1 }
--	userAuthentication OBJECT-TYPE 
--			SYNTAX      INTEGER {
--							local(1),
--							localAndradius(2),
--							localAndtacacs(3)
--						} 
--			MAX-ACCESS  read-write 
--			STATUS      current 
--			DESCRIPTION 
--					"user authentication method."
--			::= { userAuthenticationmethod 1 }
   
	-- Administration: User Account User Table
        
	adminUserTable OBJECT-TYPE 
			SYNTAX      SEQUENCE OF AdminUserEntry 
			MAX-ACCESS  not-accessible 
			STATUS      current 
			DESCRIPTION 
					"A table to management user table in the switch."
			::= { sysAdministration 2 }
        
	adminUserEntry OBJECT-TYPE
			SYNTAX      AdminUserEntry 
			MAX-ACCESS  not-accessible 
			STATUS      current 
			DESCRIPTION 
					"An entry appears in this table for each interface 
					in the system."
			INDEX { userName }
			::= { adminUserTable 1 }
           
	AdminUserEntry ::= 
			SEQUENCE { 
					userName 			SnmpAdminString,
					userPassword 		DisplayString, 
					userRowStatus		RowStatus 
			}

	userName OBJECT-TYPE 
			SYNTAX      SnmpAdminString (SIZE(1..12))
			MAX-ACCESS  read-only
			STATUS      current 
			DESCRIPTION 
					"The user name of user account."
			::= { adminUserEntry 1 }
 
 	userPassword OBJECT-TYPE 
			SYNTAX      DisplayString (SIZE(1..12))
			MAX-ACCESS  read-write 
			STATUS      current 
			DESCRIPTION 
					"The user password of user account."
			::= { adminUserEntry 2 }
 
  	userRowStatus OBJECT-TYPE
			SYNTAX      RowStatus
			MAX-ACCESS  read-create 
			STATUS      current 
			DESCRIPTION 
					"The user talbe row status."
			::= { adminUserEntry 3 }
 
	sysIGS    			OBJECT IDENTIFIER ::= { sysMulticast 2 }
	igsSystem    		OBJECT IDENTIFIER ::= { sysIGS 1 }
	igsVlan				OBJECT IDENTIFIER ::= { sysIGS 2 }

	igsStatus OBJECT-TYPE
	  SYNTAX      INTEGER  { enabled(1), disabled(2) }
	  MAX-ACCESS  read-write 
	  STATUS      current 
	  DESCRIPTION 
		 "Enables or disables IGMP/MLD snooping in the system.
		  When set to 'enabled', the Aricent IGS/MLDS module starts 
		  protocol operations.
		  When set to 'disabled', the IGS/MLDS module stops performing 
		  protocol operations."
	  DEFVAL  { 2 } 
	  ::= { igsSystem 1 }
	  
	igsHostPortPurgeInterval OBJECT-TYPE 
	  SYNTAX      Integer32 (130..153025) 
	  MAX-ACCESS  read-write 
	  STATUS      current 
	  DESCRIPTION 
		 "This is the interval (in seconds) after which a learnt  
		  port entry will be purged. For each port on which report
		  has been received this timer runs for 'PortPurgeInterval'
		  seconds. This timer will be restarted whenever a report 
		  message is received from a host on the specific port. If 
		  the timer expires, then , the learnt port entry  will 
		  be purged from the multicast group." 
	  DEFVAL  {260} 
	  ::= { igsSystem 2 }

	igsCfgQuerierStatus OBJECT-TYPE 
	  SYNTAX      INTEGER  { enabled(1), disabled(2) } 
	  MAX-ACCESS  read-write 
	  STATUS      current 
	  DESCRIPTION 
		 "The snooping switch can be configured to send IGMP/MLD queries 
		  when IGMP/MLD routers are not present in all VLAN. When set to 
		  'enabled' the switch will generate general query messages. 
		  The query messages will be suppressed if the switch receives 
		  the query message from any other router in all VLAN."
	  DEFVAL  { 2 } 
	  ::= { igsSystem 3 }
	
	igsQuerierQueryInterval OBJECT-TYPE
	  SYNTAX      Integer32 (60..600)
	  MAX-ACCESS  read-write
	  STATUS      current
	  DESCRIPTION
	  "This is the interval (in seconds) for which the switch
	  sends general queries when it is configured as a querier.
	  A switch should be configured as a querier for a VLAN
	  only when there are no queriers in the network."
	  DEFVAL { 125 }
	  ::= { igsSystem 4 }

    igsQueryMaxResponseTime OBJECT-TYPE
        SYNTAX      INTEGER (10..25)
		MAX-ACCESS  read-write
		STATUS      current
		DESCRIPTION 
        	"The maximum query response time advertised in IGMPv2 general
        	queries on this interface."
        DEFVAL     { 10 }
        ::= { igsSystem 5 }	   
        
    igsRobustnessValue OBJECT-TYPE
          SYNTAX      Integer32 (2..255)
          MAX-ACCESS  read-write
          STATUS      current
          DESCRIPTION 
	     "When the switch receives leave message on a port, it
          sends group specific query to check if there are any other 
          interested receivers for the group. This attribute defines 
          the maximum number of queries sent by the switch before deleting 
          the port from the group membership information in the forwarding 
          database. If the maximum retry count exceeds 'igsRobustnessValue', 
          then the port will be deleted from the multicast group membership
          information in the forwarding database and received leave message
          will be forwarded onto the router ports if there are no 
          interested receivers for the group." 
          DEFVAL  { 2 } 
          ::= { igsSystem 6 }   
             
    igsGrpQueryInterval OBJECT-TYPE 
          SYNTAX      Integer32 (1..25) 
          MAX-ACCESS  read-write 
          STATUS      current 
          DESCRIPTION 
             "The value of this attribute defines the time period with which 
              the switch will send group specific queries on a port to check 
              if there is any intersted receivers. The switch will send 
              'igsRobustnessValue' queries before removing the port from the 
              group membership information in the forwarding database."
          DEFVAL  { 1 }
          ::= { igsSystem 7 }       
          
    igsRouterTimeout OBJECT-TYPE 
          SYNTAX      Integer32 (120..1200) 
          MAX-ACCESS  read-write 
          STATUS      current 
          DESCRIPTION 
             "This is the interval (in seconds) after which a learnt  
              router port entry will be purged. For each router port learnt, 
              this timer runs for 'RouterPortPurgeInterval' seconds.When the 
              timer expires, the learnt router port entry is purged. However 
              if control messages are received from the router before the 
              timer expiry, then the timer is restarted."
          DEFVAL  { 250 } 
          ::= { igsSystem 8 }

    igsQuerierVersion OBJECT-TYPE
          SYNTAX      INTEGER {
						v1(1),
						v2(2),
						v3(3)
				}
          MAX-ACCESS  read-write
          STATUS      current
          DESCRIPTION
             "This object allows you to set igmp version function."
          DEFVAL  { 2 }
          ::= { igsSystem 9 }

    igsCfgFastLeaveStatus OBJECT-TYPE
          SYNTAX      INTEGER  { enabled(1), disabled(2) }
          MAX-ACCESS  read-write
          STATUS      current
          DESCRIPTION
              "Enable fast leave: while device reveive a leave message, the
               port will be removed from the group immediatly. Disable fast
               leave: while device reveive every leave message, a group
               specific query will be sent on the port."
          DEFVAL  { 1 }
          ::= { igsSystem 10 }

-- VLAN Based MAC Multicast Forwarding Table 
	igsVlanMcastMacFwdTable OBJECT-TYPE 
	  SYNTAX      SEQUENCE OF IgsVlanMcastMacFwdEntry 
	  MAX-ACCESS  not-accessible 
	  STATUS      current 
	  DESCRIPTION 
		"This table contains MAC based multicast forwarding 
		 information. This information is applicable only if
		 the 'cusSnoopMcastForwardingMode' is set to 'macbased' " 
	  ::= { igsVlan 1 }

	igsVlanMcastMacFwdEntry OBJECT-TYPE
	  SYNTAX      IgsVlanMcastMacFwdEntry
	  MAX-ACCESS  not-accessible
	  STATUS      current
	  DESCRIPTION
		"This table contains VLAN ID, multicast group MAC address and the  
		 list of ports onto which the multicast data packets for group
		 should be forwarded." 

	  INDEX {	vlanMcastMacFwdVlanId,
--				vlanMcastMacFwdVlanType,
				vlanMcastMacFwdGroupAddress	}
	  ::= { igsVlanMcastMacFwdTable 1 }

	IgsVlanMcastMacFwdEntry ::= SEQUENCE {
	  vlanMcastMacFwdVlanId				Integer32,
--	  vlanMcastMacFwdVlanType			INTEGER,
	  vlanMcastMacFwdGroupAddress		MacAddress,
	  vlanMcastMacFwdPortList			PortList 
	}

	vlanMcastMacFwdVlanId OBJECT-TYPE
	   SYNTAX      Integer32 (1..4094)
	   MAX-ACCESS  read-only
	   STATUS      current
	   DESCRIPTION
		  "VLAN ID pertaining to the Multicast forwarding entry"
	   ::= { igsVlanMcastMacFwdEntry 1 }
	  
--	vlanMcastMacFwdVlanType OBJECT-TYPE
--	  SYNTAX      INTEGER  { portBased(1), dot1q(2) } 
--	  MAX-ACCESS  read-only 
--	  STATUS      current 
--	  DESCRIPTION 
--		 "VALN type include port-based VLAN and 802.1Q VLAN."
--	  ::= { igsVlanMcastMacFwdEntry 2 } 

	vlanMcastMacFwdGroupAddress OBJECT-TYPE
	   SYNTAX      MacAddress
	   MAX-ACCESS  read-only
	   STATUS      current
	   DESCRIPTION
		   "Multicast group MAC address."
	   ::= { igsVlanMcastMacFwdEntry 3 }
	   
	vlanMcastMacFwdPortList OBJECT-TYPE
	   SYNTAX      PortList
	   MAX-ACCESS  read-only
	   STATUS      current
	   DESCRIPTION
		   "List of ports onto which the multicast data
			packets destined for this group will be forwarded."  
	   ::= { igsVlanMcastMacFwdEntry 4 }
 
-- IGS Static/Dynamic Router Port 
	igsVlanRouterPortTable OBJECT-TYPE 
	  SYNTAX      SEQUENCE OF IgsVlanRouterPortEntry 
	  MAX-ACCESS  not-accessible 
	  STATUS      current 
	  DESCRIPTION 
		"This table contains Static Router Port and Dynamic Router Port." 
	  ::= { igsVlan 2 }

	igsVlanRouterPortEntry OBJECT-TYPE
	  SYNTAX      IgsVlanRouterPortEntry
	  MAX-ACCESS  not-accessible
	  STATUS      current
	  DESCRIPTION
		"This entry contains Static Router Port and Dynamic Router Port." 

	  INDEX {	igsVlanRouterPortVlanId
--				igsVlanRouterPortVlanType
			}
	  ::= { igsVlanRouterPortTable 1 }

	IgsVlanRouterPortEntry ::= SEQUENCE {
	  igsVlanRouterPortVlanId				Integer32,
--	  igsVlanRouterPortVlanType				INTEGER,
	  igsVlanStaticRouterPortList			PortList,
	  igsVlanDynamicRouterPortList			PortList 
	}

	igsVlanRouterPortVlanId OBJECT-TYPE
	   SYNTAX      Integer32 (1..4094)
	   MAX-ACCESS  read-only
	   STATUS      current
	   DESCRIPTION
		  " VLAN ID for which snooping router port configuration is to be done."
	   ::= { igsVlanRouterPortEntry 1 }
	  
--	igsVlanRouterPortVlanType OBJECT-TYPE
--	  SYNTAX      INTEGER  { portBased(1), dot1q(2) } 
--	  MAX-ACCESS  read-only 
--	  STATUS      current 
--	  DESCRIPTION 
--		 "VALN type include port-based VLAN and 802.1Q VLAN."
--	  ::= { igsVlanRouterPortEntry 2 } 
	   
	igsVlanStaticRouterPortList OBJECT-TYPE
	   SYNTAX      PortList
	   MAX-ACCESS  read-write
	   STATUS      current
	   DESCRIPTION
		   "List of ports which are configured statically as router ports."  
	   ::= { igsVlanRouterPortEntry 3 }

	igsVlanDynamicRouterPortList OBJECT-TYPE
	   SYNTAX      PortList
	   MAX-ACCESS  read-only
	   STATUS      current
	   DESCRIPTION
		   "List of ports which are configured dynamiclly as router ports."  
	   ::= { igsVlanRouterPortEntry 4 }
	   
 -- ----------------------------------------------------------
 -- The companyVirtuaCableTest Groups
 -- ----------------------------------------------------------
 -- Virtual Cable Test Group 
 
	sysCableDiag             OBJECT IDENTIFIER ::= { sysTools 3 }
	
	cableDiagTriggerIndex OBJECT-TYPE 
           SYNTAX      Integer32
           MAX-ACCESS  read-write
           STATUS      current 
           DESCRIPTION 
              "Trigger an interface index to do virtual cable test."
           ::= {sysCableDiag 1 }  
           
	cableDiagLengthinRange  OBJECT-TYPE
           SYNTAX INTEGER  {
                  less50 (1),
                  from50to80 (2),
                  from80to100 (3),
                  from100to140 (4),
                  notAvailable (5)
           }
           MAX-ACCESS  read-only
           STATUS      current
           DESCRIPTION
              "virtual cable test length when link up in speed 1G.
               (Display in range)"
           ::= {sysCableDiag 2}

  -- VCT  Table

	cableDiagTable OBJECT-TYPE 
			SYNTAX      SEQUENCE OF CableDiagEntry 
			MAX-ACCESS  not-accessible
			STATUS      current 
			DESCRIPTION 
					"A table to get pair state and pair len."
			::= { sysCableDiag 3 }

	cableDiagEntry OBJECT-TYPE
			SYNTAX      CableDiagEntry
			MAX-ACCESS  not-accessible
			STATUS      current
			DESCRIPTION
					"An entry appears in this table for each interface
					in the system."
			INDEX { cableDiagPairIndex }
			::= { cableDiagTable 1 }

	CableDiagEntry ::=
			SEQUENCE {
					cableDiagPairIndex
						Integer32,
					cableDiagPairState
						INTEGER,
					cableDiagPairLen
					    Integer32
					}
        
	cableDiagPairIndex OBJECT-TYPE 
			SYNTAX      Integer32   (1..28)
			MAX-ACCESS  read-only 
			STATUS      current 
			DESCRIPTION 
					"The pair index of the cable for which the configuration
					in this entry applies."
			::= { cableDiagEntry 1 }

    cableDiagPairState OBJECT-TYPE
           SYNTAX INTEGER  {
                  ok (0),
                  open (1),
                  short (2), 
                  crosstalk (4),
                  notAvailable (5)
           }
           MAX-ACCESS  read-only
           STATUS      current
           DESCRIPTION
              "virtual cable test pair test result."
           ::= {cableDiagEntry 2 }

   cableDiagPairLen  OBJECT-TYPE 
           SYNTAX      Integer32 
           MAX-ACCESS  read-only
           STATUS      current
           DESCRIPTION
              "virtual cable test pair fault distance.if don't get fault len,it euqal to -1"    
            DEFVAL { -1 }
           ::= {cableDiagEntry 3}

	-- ----------------------------------------------------------------
	-- The STP group
	-- ----------------------------------------------------------------
	stpProtocolSetting  	OBJECT IDENTIFIER ::= { sysSTP 1 }
	
	stpStatus OBJECT-TYPE
	   SYNTAX   INTEGER {
					enabled(1),
					disabled(2)
				}
	   MAX-ACCESS  read-write
	   STATUS      current
	   DESCRIPTION
		  "The administrative module status requested by management for the STP
		  Module. This enables or disables STP in the system. A value of 'enabled'
		  (1) indicates that STP must be enabled in the device on all the ports.
		  A value of 'disabled'(2) indicates that STP must be disabled in the
		  device on all the ports."
	   ::= {stpProtocolSetting 1 }

	stpVersion OBJECT-TYPE
	   SYNTAX      INTEGER {
					  stpCompatible(0),
					  rstp(2),
					  mstp(3)
				   }
	   MAX-ACCESS  read-write
	   STATUS      current
	   DESCRIPTION
		   "The version of Spanning Tree Protocol the bridge is
			currently running.  The value 'stpCompatible(0)'
			indicates the Spanning Tree Protocol specified in
			IEEE 802.1D and 'rstp(2)' indicates the Rapid Spanning
			Tree Protocol specified in IEEE 802.1w and 'mstp(3)'
			indicates the Multiple Spanning Tree Protocol Specified
			in IEEE 802.1s."
	   REFERENCE
		   "IEEE 802.1D-2004"
	   DEFVAL      { rstp }
	   ::= { stpProtocolSetting 2 }
	   
	stpBridgePriority OBJECT-TYPE
	   SYNTAX      Integer32 (0..61440) 
	   MAX-ACCESS  read-write
	   STATUS      current
	   DESCRIPTION
		  "The Value of the writable portion of the Bridge
		   Identifier comprising of the first two octets.
		   The values that are set for Bridge Priority must be 
		   in steps of 4096."
	   DEFVAL {32768}
	   ::= { stpProtocolSetting 3 }
  
	stpBridgeMaxAge OBJECT-TYPE
		SYNTAX      Timeout (6..40)  
		MAX-ACCESS  read-write
		STATUS      current
		DESCRIPTION
		   "The value that all bridges use for MaxAge when
			this bridge is acting as the root. The granularity 
			of this timer is specified to be 1 second.
			An agent may return a badValue error if a set is
			attempted to a value which is not a whole number
			of seconds."
		DEFVAL {20}
		::= { stpProtocolSetting 4 }
		
	stpBridgeHelloTime OBJECT-TYPE
		SYNTAX      Timeout (1..10)
		MAX-ACCESS  read-write
		STATUS      current
		DESCRIPTION
			"The amount of time between the transmission of
			Configuration bridge PDUs by this node in units 
			of a second."
		::= { stpProtocolSetting 5 }
		
	stpBridgeForwardDelay OBJECT-TYPE
	   SYNTAX      Timeout (4..30)  
	   MAX-ACCESS  read-write
	   STATUS      current
	   DESCRIPTION
			"The value that all bridges use for ForwardDelay
			 when this bridge is acting as the root.  Note that
			 802.1D specifies that the range for this
			 parameter is related to the value of
			 BridgeMaxAge.  The granularity of this
			 timer is specified to be 1 second.
			 An agent may return a badValue error if a set is
			 attempted to a value which is not a whole number
			 of seconds."
	   DEFVAL {15}
	   ::= { stpProtocolSetting 6 }
	   
	stpMaxHopCount OBJECT-TYPE
	   SYNTAX      Integer32 (6..40)
	   MAX-ACCESS  read-write
	   STATUS      current
	   DESCRIPTION
		  "Indicates the Maximum Hop Count value. "
	   DEFVAL { 20 }
	   ::= { stpProtocolSetting 7 }
	   
	stpTxHoldCount OBJECT-TYPE
		SYNTAX      Integer32 (1..10)
		MAX-ACCESS  read-write
		STATUS      current
		DESCRIPTION
		   "The value used by the Port Transmit state machine to limit
			the maximum transmission rate."
		DEFVAL  { 6 }
		::= { stpProtocolSetting 8 }
		
	stpRootBridge OBJECT-TYPE
		SYNTAX      BridgeId  
		MAX-ACCESS  read-only
		STATUS      current
		DESCRIPTION
			"The bridge identifier of the Root of the common spanning
			 tree as determined by the Spanning Tree Protocol
			 as executed by this node.  This value is used as
			 the CIST Root Identifier parameter in all Configuration
			 Bridge PDUs originated by this node."
	   ::= { stpProtocolSetting 9 }
	   
	stpRootCost OBJECT-TYPE
	   SYNTAX      Integer32 
	   MAX-ACCESS  read-only
	   STATUS      current
	   DESCRIPTION
			"The Cost of the path to the CIST Root as seen 
			from this bridge."
	   ::= { stpProtocolSetting 10 }
	   
	stpRootMaxAge OBJECT-TYPE
	   SYNTAX      Timeout
	   UNITS       "seconds"
	   MAX-ACCESS  read-only  
	   STATUS      current
	   DESCRIPTION
			 "The maximum age of Spanning Tree Protocol
			  information learned from the network on any port
			  before it is discarded, in units of a second.  
			  This is the actual value that this
			  bridge is currently using."
	   ::= { stpProtocolSetting 11 }
	   
	stpRootForwardDelay OBJECT-TYPE
	   SYNTAX      Timeout
	   UNITS       "seconds"
	   MAX-ACCESS  read-only  
	   STATUS      current
	   DESCRIPTION
		  "This time value, measured in units of a second, 
		   controls how fast a port changes its
		   spanning state when moving towards the Forwarding
		   state.  The value determines how long the port
		   stays in a particular state before moving to the
		   next state."
	   ::= { stpProtocolSetting 12 }
	   
	stpRootPort OBJECT-TYPE
	   SYNTAX      Integer32  
	   MAX-ACCESS  read-only      
	   STATUS      current 
	   DESCRIPTION 
		  "The Port Number of the Port which offers the lowest    
		   path cost from this bridge to the CIST Root Bridge."
	   ::= { stpProtocolSetting 13 }


	-- -----------------------------------------------------------------
	-- Mst Multiple Spanning Tree Instance Port Table : CIST
	-- -----------------------------------------------------------------
	stpPortConfigurationTable OBJECT-TYPE
		SYNTAX      SEQUENCE OF StpPortEntry              
		MAX-ACCESS  not-accessible
		STATUS      current
		DESCRIPTION
			  "This table contains Common Spanning Tree Port
			   Information."
		 ::= { sysSTP 2 }
	
	stpPortConfigurationEntry OBJECT-TYPE
		  SYNTAX      StpPortEntry               
		  MAX-ACCESS  not-accessible
		  STATUS      current
		  DESCRIPTION
			  "A list of information maintained by every port for 
			  Common Spanning tree."
		  INDEX  { stpPort }
		  ::= { stpPortConfigurationTable 1 }
	
	StpPortEntry ::= 
	   SEQUENCE {
			stpPort
				Integer32,
			stpPortMstpState
				INTEGER,		
			stpPortAdminPathCost 
				Integer32,				
			stpPortPathCost 
				Integer32,				
			stpPortPriority 
				Integer32,
			stpPortAdminP2P
				INTEGER,
			stpPortState
				INTEGER,
			stpPortEdge
				INTEGER,
			stpPortRestrictedRole
				TruthValue,
			stpPortRestrictedTCN
				TruthValue,
			stpPortMigration
				TruthValue,
			stpPortDesignatedBridge
				BridgeId, 
			stpPortRole
				INTEGER
			
	}
	stpPort OBJECT-TYPE
		  SYNTAX      Integer32   (1..28)
		  MAX-ACCESS  read-only
		  STATUS      current
		  DESCRIPTION
			  "The Port number of the port for which this entry contains
			   spanning tree information."
		  ::= { stpPortConfigurationEntry 1 }
		  
		stpPortMstpState OBJECT-TYPE
		  SYNTAX      INTEGER {
					enabled(1),
					disabled(2)
				}
		  MAX-ACCESS  read-write
		  STATUS      current
		  DESCRIPTION
			  "Current state of the Port which can be changed to either 
			   Disabled or Enabled for ALL spanning tree   
			   instances. Setting this object will override the port's
			   status in any of the MSTI contexts."
		  ::= { stpPortConfigurationEntry 2 }
		
	stpPortAdminPathCost OBJECT-TYPE
		  SYNTAX      Integer32 (0..200000000)
		  MAX-ACCESS  read-write
		  STATUS      current
		  DESCRIPTION
				"The administratively assigned value for the contribution
				of this port to the path cost of paths toward the spanning
				tree root.
				Writing a value of '0' assigns the automatically calculated
				default Path Cost value to the port.  If the default Path
				Cost is being used, this object returns '0' when read."
		  ::= { stpPortConfigurationEntry 3 }
		  
	stpPortPathCost OBJECT-TYPE
		  SYNTAX      Integer32 (1..200000000)
		  MAX-ACCESS  read-only
		  STATUS      current
		  DESCRIPTION
			  "The contribution of this port to the path cost of
			   paths towards the MSTI Root which include this port."
		  ::= { stpPortConfigurationEntry 4 }
		  
	stpPortPriority OBJECT-TYPE
		  SYNTAX      Integer32 (0..240)
		  MAX-ACCESS  read-write
		  STATUS      current
		  DESCRIPTION
			  "The four most significant bits of the Port Identifier 
			  for a given Spanning Tree instance can be modified 
			  independently for each Spanning Tree instance 
			  supported by the Bridge. The values that are set for Port 
			  Priority must be in steps of 16."
		DEFVAL {128}
		  ::= { stpPortConfigurationEntry 5 }
		  
	stpPortAdminP2P OBJECT-TYPE
	   SYNTAX      INTEGER {               
					 forceTrue(0),
					 forceFalse(1),
					 auto(2)
				   }
	   MAX-ACCESS  read-write
	   STATUS      current
	   DESCRIPTION
		  "The administrative point-to-point status of the LAN segment
		   attached to this port.  A value of forceTrue(0) indicates that
		   this port should always be treated as if it is connected to
		   a point-to-point link.  A value of forceFalse(1) indicates
		   that this port should be treated as having a shared media
		   connection.  A value of auto(2) indicates that this port is
		   considered to have a point-to-point link if it is an Aggregator
		   and all of its members are aggregatable, or if the MAC entity
		   is configured for full duplex operation, either through
		   auto-negotiation or by management means."
		::= { stpPortConfigurationEntry 6 }
		
	stpPortState OBJECT-TYPE
		SYNTAX      INTEGER {              
                  disabled (1),
                  discarding (2),
                  learning (4),
                  forwarding (5)
                  }
      MAX-ACCESS  read-only            
      STATUS      current
      DESCRIPTION
          "Current state of the Port as defined by the Common    
           spanning tree protocol." 
      ::= { stpPortConfigurationEntry 7 }
	 
	stpPortEdge OBJECT-TYPE
		SYNTAX    INTEGER {               
					forceTrue(0),
					forceFalse(1),
					auto(2)
				 }
		MAX-ACCESS  read-write
		STATUS      current
		DESCRIPTION
			"The administrative value of the Edge Port parameter.  A
			value of forceTrue(0) indicates that this port should be
			assumed as an edge-port and a value of forceFalse(1) indicates
			that this port should be assumed as a non-edge-port.auto 
			indicates that detection of a port as Edge Port happens automatically"
		::= { stpPortConfigurationEntry 8 }
		
	stpPortRestrictedRole OBJECT-TYPE 
		SYNTAX      TruthValue 
		MAX-ACCESS  read-write 
		STATUS      current 
		DESCRIPTION 
			"A Boolean value set by management. If TRUE causes the Port not 
			 to be selected as Root Port for the CIST or any MSTI, even it has 
			 the best spanning tree priority vector. Such a Port will be selected 
			 as an Alternate Port after the Root Port has been selected. This 
			 parameter should be FALSE by default. If set it can cause lack of 
			 spanning tree connectivity. It is set by a network administrator to 
			 prevent bridges external to a core region of the network influencing 
			 the spanning tree active topology, possibly because those bridges are 
			 not under the full control of the administrator.
			 This administrator configuration is also known as 'Root Guard'."
		::= {stpPortConfigurationEntry 9}

	stpPortRestrictedTCN OBJECT-TYPE 
		SYNTAX      TruthValue 
		MAX-ACCESS  read-write 
		STATUS      current 
		DESCRIPTION 
			"A Boolean value set by management. If TRUE causes the Port not 
			 to propagate received topology change notifications and topology 
			 changes to other Ports. This parameter should be FALSE by default. 
			 If set it can cause temporary loss of connectivity after changes in 
			 a spanning trees active topology as a result of persistent 
			 incorrectly learnt station location information. It is set by a 
			 network administrator to prevent bridges external to a core region of 
			 the network causing address flushing in that region, possibly because 
			 those bridges are not under the full control of the administrator or 
			 MAC_Operational for the attached LANs transitions frequently." 
		::= {stpPortConfigurationEntry 10}
		
	stpPortMigration OBJECT-TYPE
		SYNTAX      TruthValue                
		MAX-ACCESS  read-write           
		STATUS      current
		DESCRIPTION
		  "Indicates the Protocol migration state of this Port.         
		   When operating in RSTP/MSTP (version >= 2) mode, writing 
		   TRUE(1) to this object forces this port to transmit MSTP 
		   BPDUs without instance information.
		   Any other operation on this object has no effect and
		   it always returns FALSE(2) when read."
		::= { stpPortConfigurationEntry 11 }
	stpPortDesignatedBridge OBJECT-TYPE
      SYNTAX      BridgeId                 
      MAX-ACCESS  read-only            
      STATUS      current
      DESCRIPTION
          "The unique Bridge Identifier of the bridge which this port  
           considers to be the Designated Bridge for the port's segment."   
      ::= { stpPortConfigurationEntry 12 }
	stpPortRole OBJECT-TYPE
      SYNTAX      INTEGER {              
                   disabled(0),
                   alternate(1),
                   backup(2),
                   root(3),
                   designated(4)
                  }
      MAX-ACCESS  read-only        
      STATUS      current
      DESCRIPTION
          "Current Port Role of the port for this spanning 
          tree instance."                                      
      ::= { stpPortConfigurationEntry 13 }

	-- ----------------------------------------------------------------
	-- The MST Configuration Identification
	-- ----------------------------------------------------------------
	mstConfiguration  OBJECT IDENTIFIER ::= { sysSTP 3 }
	
	mstiConfigurationName OBJECT-TYPE
	   SYNTAX      DisplayString (SIZE (0..32))
	   MAX-ACCESS  read-write 
	   STATUS      current
	   DESCRIPTION
		  "The Name for the Region's configuration. By Default 
		   Region Name will be equal to the Bridge Mac Address."
	   ::= { mstConfiguration 1 } 
	
	mstiRevisionLevel OBJECT-TYPE
	   SYNTAX      Integer32 (0..65535)
	   MAX-ACCESS  read-write 
	   STATUS      current
	   DESCRIPTION
		  "Version of the MST Region."
	   ::= { mstConfiguration 2 }
	-- -----------------------------------------------------------------
	-- Future Mst VlanId to Instance Mapping Table : MSTI             
	-- -----------------------------------------------------------------        
	mstVlanMstiMappingTable OBJECT-TYPE
		SYNTAX      SEQUENCE OF MstVlanMstiMappingEntry
		MAX-ACCESS  not-accessible
		STATUS      current
		DESCRIPTION
			  "This table contains one entry for each instance of MSTP. 
			   This table maintains context ID as one more index to 
			   support Multiple Instances." 
		::= { mstConfiguration 3 }
	
	mstVlanMstiMappingEntry OBJECT-TYPE
		 SYNTAX      MstVlanMstiMappingEntry
		 MAX-ACCESS  not-accessible
		 STATUS      current
		 DESCRIPTION
			 "A conceptual row containing the status of the MSTP instance."
			  INDEX  { mstVlanInstanceIndex }
		 ::= { mstVlanMstiMappingTable 1 }
	
	MstVlanMstiMappingEntry ::= 
	   SEQUENCE {
		   mstVlanInstanceIndex  
				Integer32,
		   mstSetVlanList 
				OCTET STRING,
		   mstResetVlanList 
				OCTET STRING,
		   mstInstanceVlanMapped 
				OCTET STRING,
		   mstInstanceVlanMapped2k 
				OCTET STRING,
		   mstInstanceVlanMapped3k 
				OCTET STRING,
		   mstInstanceVlanMapped4k 
				OCTET STRING,
			mstMstiBridgePriority
			        Integer32
	   }
	
	mstVlanInstanceIndex OBJECT-TYPE
		  SYNTAX      Integer32 (1..15)
		  MAX-ACCESS  read-only
		  STATUS      current
		  DESCRIPTION
			  "An arbitrary integer within the range from 1 to the value of
			   Max Instance Number that uniquely identifies an instance."
		  ::= { mstVlanMstiMappingEntry 1 }
	
	mstSetVlanList OBJECT-TYPE
		SYNTAX     OCTET STRING (SIZE (0..512))
		MAX-ACCESS read-write
		STATUS     current
		DESCRIPTION
		 "A string of octets containing one bit per VLAN. The
		  first octet corresponds to VLANs with VlanIndex values
		  1 through 8; the second octet to VLANs 9 through
		  16 etc.  The most significant bit of each octet
		  corresponds to the lowest VlanIndex value in that octet.
		  The set of vlans configured by management to map for this 
		  Instance.  If the VlanId to Instance Mapping has to be known
		  then any one of the VlanMapped object should be used.If a 
		  vlan is already mapped to this Instance, it may not be mapped 
		  again. This object is used only for SET operation.
		  GET Operation returns null values."
		::= { mstVlanMstiMappingEntry 2 }
	
	mstResetVlanList OBJECT-TYPE
		SYNTAX     OCTET STRING (SIZE (0..512))
		MAX-ACCESS read-write
		STATUS     current
		DESCRIPTION
		 "A string of octets containing one bit per VLAN. The
		  first octet corresponds to VLANs with VlanIndex values
		  1 through 8; the second octet to VLANs 9 through
		  16 etc.  The most significant bit of each octet
		  corresponds to the lowest VlanIndex value in that octet.
		  The set of vlans configured by management to unmap from this 
		  Instance. A vlan may not be unmapped from this instance if 
		  it is not already mapped to this Instance. This object is
		  used only for SET operation.GET Operation returns null values."
		::= { mstVlanMstiMappingEntry 3 }
	
	mstInstanceVlanMapped OBJECT-TYPE
		SYNTAX     OCTET STRING (SIZE (0..128))
		MAX-ACCESS read-only
		STATUS     current
		DESCRIPTION
				"A string of octets containing one bit per VLAN. The
				first octet corresponds to VLANs with VlanIndex values
				1 through 8; the second octet to VLANs 9 through
				16 etc.  The most significant bit of each octet
				corresponds to the lowest VlanIndex value in that octet.
	
				For each VLAN that is mapped to this MSTP instance,
				the bit corresponding to that VLAN is set to '1'."
		::= { mstVlanMstiMappingEntry 4 }
	
	mstInstanceVlanMapped2k OBJECT-TYPE
		SYNTAX     OCTET STRING (SIZE (0..128))
		MAX-ACCESS read-only
		STATUS     current
		DESCRIPTION
				"A string of octets containing one bit per VLAN for
				VLANS with VlanIndex values 1024 through 2047. The
				first octet corresponds to VLANs with VlanIndex values
				1024 through 1031; the second octet to VLANs 1032
				through 1039 etc.  The most significant bit of each
				octet corresponds to the lowest VlanIndex value in that
				octet.
	
				For each VLAN that is mapped to this MSTP instance,
				the bit corresponding to that VLAN is set to '1'.
				
				This object is only instantiated on devices with 
				support for VlanIndex values up to 4095."
		::= { mstVlanMstiMappingEntry 5 }
	
	mstInstanceVlanMapped3k OBJECT-TYPE
		SYNTAX     OCTET STRING (SIZE (0..128))
		MAX-ACCESS read-only
		STATUS     current
		DESCRIPTION
				"A string of octets containing one bit per VLAN for
				VLANS with VlanIndex values 2048 through 3071. The
				first octet corresponds to VLANs with VlanIndex values
				of 2048 through 2055; the second octet to VLANs 2056
				through 2063 etc.  The most significant bit of each
				octet corresponds to the lowest VlanIndex value in that
				octet.
	
				For each VLAN that is mapped to this MSTP instance,
				the bit corresponding to that VLAN is set to '1'.
	
				This object is only instantiated on devices with 
				support for VlanIndex values up to 4095."
		::= { mstVlanMstiMappingEntry 6 }
	
	mstInstanceVlanMapped4k OBJECT-TYPE
		SYNTAX     OCTET STRING (SIZE (0..128))
		MAX-ACCESS read-only
		STATUS     current
		DESCRIPTION
				"A string of octets containing one bit per VLAN for
				VLANS with VlanIndex values 3072 through 4095. The
				first octet corresponds to VLANs with VlanIndex values
				3072 through 3079; the second octet to VLANs 3080
				through 3087 etc.  The most significant bit of each
				octet corresponds to the lowest VlanIndex value in that
				octet.
	
				For each VLAN that is mapped to this MSTP instance,
				the bit corresponding to that VLAN is set to '1'.
	
				This object is only instantiated on devices with 
				support for VlanIndex values up to 4095."
		::= { mstVlanMstiMappingEntry 7 }
	mstMstiBridgePriority OBJECT-TYPE
	   SYNTAX      Integer32 (0..61440) 
	   MAX-ACCESS  read-write     
	   STATUS      current 
	   DESCRIPTION 
		  "The writable portion of the MSTI Bridge Identifier.
		   comprising of the first two octets.
		   The values that are set for Bridge Priority must be 
		   in steps of 4096."
	   DEFVAL {32768}
	   ::= { mstVlanMstiMappingEntry 8 }
	   
	mstInstanceTable OBJECT-TYPE
		SYNTAX      SEQUENCE OF MstInstanceEntry
		MAX-ACCESS  not-accessible
		STATUS      current
		DESCRIPTION
			  "This table contains one entry for each instance of MSTP. 
			   This table maintains context ID as one more index to 
			   support Multiple Instances." 
		::= { sysSTP 4 }
	
	mstInstanceEntry OBJECT-TYPE
		 SYNTAX      MstInstanceEntry
		 MAX-ACCESS  not-accessible
		 STATUS      current
		 DESCRIPTION
			 "A conceptual row containing the status of the MSTP instance."
			  INDEX  { mstInstanceIndex }
		 ::= { mstInstanceTable 1 }
	
	MstInstanceEntry ::= 
	   SEQUENCE {
		   mstInstanceIndex  
				Integer32,
		   mstRootCost 
				Integer32,
		   mstRootPort 
				Integer32,
		   mstBridgeRegionalRoot 
				BridgeId,
		   mstDesignatedBridge 
				BridgeId,
		   mstBridgePriority 
				Integer32
	   }
    mstInstanceIndex OBJECT-TYPE
		SYNTAX      Integer32 (1..15)
		MAX-ACCESS  read-only 
		STATUS      current 
		DESCRIPTION 
		"Spanning Tree Instance to which the information belongs."
		::= { mstInstanceEntry 1 }
	mstRootCost OBJECT-TYPE
	   SYNTAX      Integer32  
	   MAX-ACCESS  read-only      
	   STATUS      current 
	   DESCRIPTION 
		  "The Cost of the path to the MSTI Regional Root as seen 
		   by this bridge." 
	   ::= { mstInstanceEntry 2 }
	mstRootPort OBJECT-TYPE
	   SYNTAX      Integer32  
	   MAX-ACCESS  read-only      
	   STATUS      current 
	   DESCRIPTION 
		  "The Port Number of the Port which offers the lowest    
		   path cost from this bridge to the MSTI Region Root Bridge."
	   ::= { mstInstanceEntry 3 }	
	mstBridgeRegionalRoot OBJECT-TYPE
	   SYNTAX      BridgeId  
	   MAX-ACCESS  read-only      
	   STATUS      current 
	   DESCRIPTION 
		  "MSTI Regional Root Identifier value for the Instance. This value 
		   is used as the MSTI Regional Root Identifier parameter in all
		   Configuration Bridge PDUs originated by this node"
	   ::= { mstInstanceEntry 4 }
	mstDesignatedBridge OBJECT-TYPE
		SYNTAX      BridgeId                 
		MAX-ACCESS  read-only            
		STATUS      current
		DESCRIPTION
		  "The unique Bridge Identifier of the bridge which this port  
		   considers to be the Designated Bridge for the port's segment."   
		::= { mstInstanceEntry 5 }
	mstBridgePriority OBJECT-TYPE
		SYNTAX      Integer32 (0..61440) 
		MAX-ACCESS  read-write     
		STATUS      current 
		DESCRIPTION 
		  "The writable portion of the MSTI Bridge Identifier.
		   comprising of the first two octets.
		   The values that are set for Bridge Priority must be 
		   in steps of 4096."
		DEFVAL {32768}
		::= { mstInstanceEntry 6 }
	mstMstiPortTable OBJECT-TYPE
            SYNTAX      SEQUENCE OF MstMstiPortEntry              
            MAX-ACCESS  not-accessible
            STATUS      current
            DESCRIPTION
                  "This table contains Spanning Tree Instance Specific Port
                   Information."
             ::= { sysSTP 5 }
	
	mstMstiPortEntry OBJECT-TYPE
		  SYNTAX      MstMstiPortEntry               
		  MAX-ACCESS  not-accessible
		  STATUS      current
		  DESCRIPTION
			  "A list of information maintained by every port for each 
			   and every spanning tree instance."
		  INDEX  { mstMstiPort, mstpMstiInstanceIndex }
		  ::= { mstMstiPortTable 1 }
	
	MstMstiPortEntry ::= 
	   SEQUENCE {
		   mstMstiPort  
				Integer32,   
		   mstpMstiInstanceIndex
		         Integer32,
		   mstMstiPortDesignatedBridge 
				BridgeId,
		   mstMstiPortAdminPathCost 
				Integer32,
		   mstMstiPortPathCost 
				Integer32,
		   mstMstiPortPriority 
				Integer32,
		   mstMstiPortState 
				INTEGER,
		   mstMstiCurrentPortRole  
				INTEGER
	}
	
	mstMstiPort OBJECT-TYPE
		  SYNTAX      Integer32   (1..28)
		  MAX-ACCESS  read-only
		  STATUS      current
		  DESCRIPTION
			  "The Port number of the port for which this entry contains   
			   spanning tree information."                                      
		  ::= { mstMstiPortEntry 1 }
		  
	mstpMstiInstanceIndex OBJECT-TYPE
		  SYNTAX      Integer32 (1..64|4094)
		  MAX-ACCESS  read-only
		  STATUS      current
		  DESCRIPTION
			  "An arbitrary integer within the range from 1 to the value of
			   Max Instance Number that uniquely identifies an instance. In
			   a Bridge that supports PBB-TE, the special MSTID of 4094, the
			   PTETID, identifies VIDs that can be used by Ethernet Switched
			   Paths (ESPs). ESPs are provisioned seperately by any external agent
			   and do not use spanning tree."
		  ::= { mstMstiPortEntry 2 }
	  
	mstMstiPortDesignatedBridge OBJECT-TYPE
		  SYNTAX      BridgeId                 
		  MAX-ACCESS  read-only            
		  STATUS      current
		  DESCRIPTION
			  "The unique Bridge Identifier of the bridge which this port  
			   considers to be the Designated Bridge for the port's segment."   
		  ::= { mstMstiPortEntry 3 }
	
	mstMstiPortAdminPathCost OBJECT-TYPE
		  SYNTAX      Integer32 (0..200000000)
		  MAX-ACCESS  read-write           
		  STATUS      current
		  DESCRIPTION
			  "The contribution of this port to the path cost of
			   paths towards the MSTI Root which include this port."
		  ::= { mstMstiPortEntry 4 }
	
	mstMstiPortPathCost OBJECT-TYPE
		  SYNTAX      Integer32 (1..200000000)
		  MAX-ACCESS  read-only           
		  STATUS      current
		  DESCRIPTION
			  "The contribution of this port to the path cost of
			   paths towards the MSTI Root which include this port."
		  ::= { mstMstiPortEntry 5 }
	
	mstMstiPortPriority OBJECT-TYPE
		  SYNTAX      Integer32 (0..240)
		  MAX-ACCESS  read-write           
		  STATUS      current
		  DESCRIPTION
			  "The four most significant bits of the Port Identifier 
			  for a given Spanning Tree instance can be modified 
			  independently for each Spanning Tree instance 
			  supported by the Bridge. The values that are set for Port 
			  Priority must be in steps of 16."
		DEFVAL {128}
		  ::= { mstMstiPortEntry 6 }
	
	mstMstiPortState OBJECT-TYPE
		  SYNTAX      INTEGER {              
                  disabled (1),
                  discarding (2),
                  learning (4),
                  forwarding (5)
                  }
		  MAX-ACCESS  read-only           
		  STATUS      current
		  DESCRIPTION
			  "Current state of the Port as defined by the Multiple  
			 	spanning tree protocol. Port which is Forwarding state
			 	in one instance can be in Discarding (Blocking) state 
			 	in another instance"                                            
		  ::= { mstMstiPortEntry 7 }
		        
	mstMstiCurrentPortRole OBJECT-TYPE
		  SYNTAX      INTEGER {              
					   disabled(0),
					   alternate(1),
					   backup(2),
					   root(3),
					   designated(4),
					   master(5)
					  }
		  MAX-ACCESS  read-only        
		  STATUS      current
		  DESCRIPTION
			  "Current Port Role of the port for this spanning 
			  tree instance."                                      
		  ::= { mstMstiPortEntry 8 }

    -- ---------------------------------------------------------------------
    -- voicevlan Function
    -- ---------------------------------------------------------------------
          
	voiceVlanSystem          OBJECT IDENTIFIER ::= { sysVoiceVlan 1 }
	voiceVlanOui             OBJECT IDENTIFIER ::= { sysVoiceVlan 2 }
 
    -- ------------------------------------------------------------------
    -- The Voice Vlan Group
    -- ------------------------------------------------------------------

	voiceVlanMode OBJECT-TYPE
		SYNTAX      INTEGER { enabled(1), disabled(2) }
		MAX-ACCESS  read-write
		STATUS      current
		DESCRIPTION
			"Voice VLAN is a feature that allows you to automatically place 
			the voice traffic from IP phone to an assigned VLAN to enhance 
			the VoIP service. 
			This object is for enabling or disabling Voice Vlan function 
			in the system. 
			If the Vlan mode is in Asymmetric VLAN mode, Voice VLAN can not 
			be enabled."

		::= { voiceVlanSystem 2 }

	voiceVlanId OBJECT-TYPE
		SYNTAX INTEGER
		MAX-ACCESS read-write
		STATUS current
		DESCRIPTION
			"The ID of VLAN that you want the voice traffic to be in. 
			It must be a exist vlan id."
		::= { voiceVlanSystem 3 }

	voiceVlanTimeout OBJECT-TYPE
		SYNTAX INTEGER
		MAX-ACCESS read-write
		STATUS current
		DESCRIPTION
			"A period of time in hour to remove a port from voice VLAN 
			if the port is an automatic VLAN member.
			The Timeout range is 1~120 hours.
			Default aging time is 1 hour."
		::= { voiceVlanSystem 4}

	voiceVlanPriority OBJECT-TYPE
		SYNTAX      Integer32 (0..7)
		MAX-ACCESS read-write
		STATUS current
		DESCRIPTION
			"The 802.1p priority levels of the traffic in the Voice VLAN."
		::= { voiceVlanSystem 5}

        --
        -- Voice Vlan Port Control Table
        --          

	voiceVlanPortCtrlTable OBJECT-TYPE
		SYNTAX      SEQUENCE OF VoiceVlanPortCtrlEntry
		MAX-ACCESS  not-accessible
		STATUS      current
		DESCRIPTION
			"A table that contains Voice Vlan Port Control
			configuration information."
		::= { voiceVlanSystem 6 }


	voiceVlanPortCtrlEntry OBJECT-TYPE
		SYNTAX      VoiceVlanPortCtrlEntry
		MAX-ACCESS  not-accessible
		STATUS      current
		DESCRIPTION
			"A list of Voice Vlan Control configuration
			parameters for each Port on this device."
		INDEX      { voiceVlanPortCtrlIndex }
		::= { voiceVlanPortCtrlTable 1 }  

	VoiceVlanPortCtrlEntry ::=
		SEQUENCE {
            voiceVlanPortCtrlIndex
                InterfaceIndex,
            voiceVlanPortAutoDetection
                INTEGER,    
            voiceVlanPortState
                INTEGER        
        }
        
	voiceVlanPortCtrlIndex OBJECT-TYPE
		SYNTAX       InterfaceIndex
		MAX-ACCESS   read-only
		STATUS       current
		DESCRIPTION
		  "The voice vlan port index."
		::= { voiceVlanPortCtrlEntry 1 }            
          
	voiceVlanPortAutoDetection  OBJECT-TYPE
		SYNTAX       INTEGER { enabled(1), disabled(2) }
		MAX-ACCESS   read-write
		STATUS       current
		DESCRIPTION
            "This object is for enabling or disabling Voice Vlan Auto 
             Detection in the port.
             If the auto detection is enable, switch will add this port 
             to the voice VLAN automatically if it detects the device OUI 
             matches the Telephony OUI.
             If the port is a static member of voice vlan or a LA member,
             it can not enable voice vlan auto detection."
		::= { voiceVlanPortCtrlEntry 2 }
                
	voiceVlanPortState      OBJECT-TYPE 
		SYNTAX INTEGER  {
			manual(1),
			dynamic(2),
			none(3)
		}
		MAX-ACCESS  read-only 
		STATUS      current 
		DESCRIPTION 
			"This object indicates Voice vlan state to this Port.
			manual - this port is a static member of voice vlan.
			dynamic - this port is a dynamic member of voice vlan.
			none - this port is not a member of voice vlan."
			 
		::= { voiceVlanPortCtrlEntry 3 }    

    -- ------------------------------------------------------------------
    -- The Voice Vlan OUI Group
    -- ------------------------------------------------------------------

    --
    -- Voice Vlan OUI Table
    --
    
    voiceVlanOuiTable  OBJECT-TYPE
        SYNTAX     SEQUENCE OF VoiceVlanOuiEntry 
        MAX-ACCESS not-accessible
        STATUS     current
        DESCRIPTION
			"A voice vlan OUI entry containing the description and mac."

        ::= { voiceVlanOui 1 }

    voiceVlanOuiEntry OBJECT-TYPE
        SYNTAX     VoiceVlanOuiEntry
        MAX-ACCESS not-accessible
        STATUS     current
        DESCRIPTION
              "A voice vlan OUI entry containing the description and mac."

        INDEX { voiceVlanOuiTelephonyOui }
        ::= { voiceVlanOuiTable 1 }

    VoiceVlanOuiEntry  ::=
		SEQUENCE {
			voiceVlanOuiTelephonyOui          MacAddress,
			voiceVlanOuiDescription           DisplayString,
			voiceVlanOuiMask                  MacAddress,
			voiceVlanOuiStatus                RowStatus
		}

    voiceVlanOuiTelephonyOui OBJECT-TYPE
		SYNTAX       MacAddress
		MAX-ACCESS   read-only
		STATUS       current
		DESCRIPTION
			 "An Organizationally Unique Identifier (OUI) is a 24-bit number 
			 that is purchased from the IEEE Registration Authority. This identifier 
			 uniquely identifies a vendor, manufacturer, or other organization.
			 This object indicates the voice traffic's OUI that user created." 
		::= { voiceVlanOuiEntry  1 }

    voiceVlanOuiDescription OBJECT-TYPE
        SYNTAX      DisplayString
        MAX-ACCESS  read-write
        STATUS      current
        DESCRIPTION
			"The Description for the OUI."
        ::= { voiceVlanOuiEntry  2 }
        
    voiceVlanOuiMask OBJECT-TYPE
		SYNTAX       MacAddress
		MAX-ACCESS   read-only
		STATUS       current
		DESCRIPTION
			"Voice vlan OUI Mask. Always be FF:FF:FF:00:00:00."
		::= { voiceVlanOuiEntry  3 }
        
    voiceVlanOuiStatus OBJECT-TYPE
		SYNTAX RowStatus
		MAX-ACCESS read-write
		STATUS current
		DESCRIPTION
			"This object indicates the status of this entry. 
			To create a new entry, you must set the voiceVlanOuiStatus 
			to be CreateAndGo, then this entry will turn to be Active."
		::= { voiceVlanOuiEntry 4 }
	
	tacacsServerTable OBJECT-TYPE
		SYNTAX SEQUENCE OF TacacsServerEntry
		MAX-ACCESS not-accessible
		STATUS current
		DESCRIPTION
			"The TACACS+ server(IPv4 or IPv6) table of server information entries. The entries have
			server information such as server IP address, secret key, port no and timeout."
		::=  { sysTacacs 1 }

	tacacsServerEntry OBJECT-TYPE
		SYNTAX TacacsServerEntry
		MAX-ACCESS not-accessible
		STATUS current
		DESCRIPTION
			"The entry has server address type, server IP address, port no. secret key and timeout."
		INDEX {tacacsServerAddrType, tacacsServerAddress}
		::=  { tacacsServerTable 1 }

	TacacsServerEntry ::= SEQUENCE {
		tacacsServerAddrType		InetAddressType,
		tacacsServerAddress			InetAddress,
		tacacsServerInterfaceName	OCTET STRING,
		tacacsServerPort 			Integer32,
		tacacsServerTimeout  		Integer32,
		tacacsServerKey				DisplayString,
		tacacsServerRowStatus		RowStatus,
		tacacsServerPriority		Integer32
	   }


	tacacsServerAddrType OBJECT-TYPE
		SYNTAX InetAddressType
		MAX-ACCESS read-only
		STATUS current
		DESCRIPTION
			"The type of IP address used.This can be IPv4 or IPv6."
		::=  { tacacsServerEntry 1 }

	tacacsServerAddress OBJECT-TYPE
		SYNTAX InetAddress
		MAX-ACCESS read-only
		STATUS current
		DESCRIPTION
			"Server IP address"
		::=  { tacacsServerEntry 2 }

	tacacsServerInterfaceName OBJECT-TYPE
		SYNTAX      OCTET STRING (SIZE(1..32))
		MAX-ACCESS  read-only
		STATUS      current
		DESCRIPTION
			"Specifies the interface name from which the TACACS+ server will be connected when server address is linklocal address."
		::= { tacacsServerEntry 3 }
		
	tacacsServerPort OBJECT-TYPE
		SYNTAX Integer32
		MAX-ACCESS read-write
		STATUS current
		DESCRIPTION
			"Server port no. for TACACS+ protocol. The default value is 49."
		DEFVAL { 49 }
		::=  { tacacsServerEntry 4 }

	tacacsServerTimeout OBJECT-TYPE
		SYNTAX Integer32 (1..255)
		MAX-ACCESS read-write
		STATUS current
		DESCRIPTION
			"The time out value within which a response is expected from server(IPv4 or IPv6). The session will be released, 
			if the response is not received within this time out."
		::=  { tacacsServerEntry 5 }

	tacacsServerKey OBJECT-TYPE
		SYNTAX DisplayString
		MAX-ACCESS read-write
		STATUS current
		DESCRIPTION
			"Secret key shared between the client and server(IPv4 or IPv6) for encryption and
			decryption"
		::=  { tacacsServerEntry 6 }
		
	tacacsServerRowStatus OBJECT-TYPE
		SYNTAX RowStatus
		MAX-ACCESS read-write
		STATUS current
		DESCRIPTION
			"Row status of the server(IPv4 or IPv6) entry."
		::=  { tacacsServerEntry 7 }
	
	tacacsServerPriority 	OBJECT-TYPE
	SYNTAX      Integer32 (1..5)
	MAX-ACCESS  read-write
	STATUS      current
	DESCRIPTION
		"Specifies the server priority, higher priority with lower integger value"
	::= { tacacsServerEntry 8 }
	
-- ----------------------------------------------------------
-- The RADIUS Groups
-- ----------------------------------------------------------
		radiusServerTable OBJECT-TYPE
			SYNTAX SEQUENCE OF RadiusServerEntry
			MAX-ACCESS not-accessible
			STATUS current
			DESCRIPTION
				"The (conceptual) table listing the RADIUS servers with
				         which the client shares a secret."
			::=  { sysRadius 1 }

		radiusServerEntry OBJECT-TYPE
			SYNTAX RadiusServerEntry
			MAX-ACCESS not-accessible
			STATUS current
			DESCRIPTION
				"An entry (conceptual row) representing a RADIUS server
				         with which the client shares a secret."
			INDEX {radiusServerIndex}
			::=  { radiusServerTable 1 }

		RadiusServerEntry ::= SEQUENCE {
			radiusServerIndex    	INTEGER,
			radiusServerAddrType	INTEGER,
			radiusServerAddress  	InetAddress,
			radiusServerInterfaceName	OCTET STRING,
			radiusClientServerPortNumber Integer32,
			radiusAccClientServerPortNumber	Integer32,
			radiusServerSharedSecret    DisplayString,
			radiusServerEntryRowStatus		RowStatus
		   }


		radiusServerIndex OBJECT-TYPE
			SYNTAX INTEGER   (1..5)
			MAX-ACCESS read-only
			STATUS current
			DESCRIPTION
				"The RADIUS server with whom the client interacts."
			::=  { radiusServerEntry 1 }

		radiusServerAddrType OBJECT-TYPE
			SYNTAX INTEGER {
						ipv4 (1),
				        ipv6 (2)
					}
			MAX-ACCESS read-write
			STATUS current
			DESCRIPTION
				"The IP address type of the RADIUS server
				         referred to in this table entry."
			::=  { radiusServerEntry 2 }

		radiusServerAddress OBJECT-TYPE
			SYNTAX InetAddress
			MAX-ACCESS read-write
			STATUS current
			DESCRIPTION
				"The IP address of the RADIUS server
				         referred to in this table entry."
			::=  { radiusServerEntry 3 }

		radiusServerInterfaceName OBJECT-TYPE
               SYNTAX      OCTET STRING (SIZE(1..32))
               MAX-ACCESS  read-only
               STATUS      current
               DESCRIPTION
                   "Specifies the interface name when the radiusServerAddress is linklocal address."
               ::= { radiusServerEntry 4 } 
			   
		radiusClientServerPortNumber  OBJECT-TYPE
			SYNTAX Integer32 (1..65535)
			MAX-ACCESS read-write
			STATUS current
			DESCRIPTION
				"The UDP port that the client uses to send requests to
				 this server."
			::= { radiusServerEntry 5 }

		radiusAccClientServerPortNumber  OBJECT-TYPE
			  SYNTAX Integer32 (1..65535)
			  MAX-ACCESS read-write
			  STATUS current
			  DESCRIPTION
					"The UDP port that the client is using to send requests to
					 this server."
			  ::= { radiusServerEntry 6 }
			  
		radiusServerSharedSecret OBJECT-TYPE
			SYNTAX DisplayString
			MAX-ACCESS read-write
			STATUS current
			DESCRIPTION
				"The secret string which is shared between Server and Client"
			::=  { radiusServerEntry 7 }

		radiusServerEntryRowStatus	OBJECT-TYPE
		   SYNTAX    			RowStatus
		   MAX-ACCESS 			read-write
		   STATUS 			current
		   DESCRIPTION
			  "The status of the entry can be used as specified in the SNMP V2
			  standard. "
		  ::=  { radiusServerEntry 8 } 

	-- ----------------------------------------------------------------
    -- The SSL group
    -- ---------------------------------------------------------------- 
	sslGeneralGroup         OBJECT IDENTIFIER ::= { sysSSL 1 }

-- General Group
	sslSecureHttpStatus OBJECT-TYPE 
		SYNTAX      INTEGER {
						  enabled      (1),
						  disabled	   (2)
				    }
		MAX-ACCESS  read-write 
		STATUS      current 
		DESCRIPTION 
		  "This object is used for enable/disable secure HTTP in the system."

		DEFVAL  { disabled } 
		::= { sslGeneralGroup 1 }
		
-- ----------------------------------------------------------
-- The PNAC Groups
-- ----------------------------------------------------------
   pnacGlobal			OBJECT IDENTIFIER ::= { sysPNAC 1 }
   -- --------------------------------------------------------------
   -- PNAC Gloabal info.
   -- --------------------------------------------------------------
	pnacAuthStatus OBJECT-TYPE
		SYNTAX INTEGER {
				   enabled(1),
				   disabled(2)
		}
		MAX-ACCESS 			read-write
		STATUS              current
		DESCRIPTION
		"Enable/Disable Static 802.1x."
		::= { pnacGlobal 1 }   
	
	pnacNasId OBJECT-TYPE 
		SYNTAX      DisplayString(SIZE(0..16)) 
		MAX-ACCESS  read-write 
		STATUS      current 
		DESCRIPTION  
		  "This object is the Network Access Server Identifier 
		  to be presented before the remote Authentication 
		  Server." 
		::= { pnacGlobal 2}
	
	pnacAuthServerType OBJECT-TYPE 
		SYNTAX INTEGER {
				   radiusServer(1),
				   tacacsplusServer(2),
				   localServer(3)
		} 
		MAX-ACCESS  read-write 
		STATUS      current 
		DESCRIPTION 
		  "This object is used by the Authenticator for its 
		  authentication services, to configure the choice of  
		  RADIUS or TACACS+ remote authentication servers when
		  the authentication method is through a remote server,
		  that is, this object can be configured only if 
		  cusPnacAuthenticServer is set to remoteServer." 
		DEFVAL  { 3 } 
		::= { pnacGlobal 3 }
   -- --------------------------------------------------------------
   -- PNAC Port Authmode info.
   -- --------------------------------------------------------------		
	pnacPaePortTable OBJECT-TYPE 
		SYNTAX      SEQUENCE OF PnacPaePortEntry 
		MAX-ACCESS  not-accessible 
		STATUS      current 
		DESCRIPTION 
		 "A table of system level information for each port 
		 supported by the AricentPNAC. An entry appears in this 
		 table for each port of this system. This table is an 
		 extension of dot1xPaePortTable of IEEE 802.1x MIB." 
		::= { sysPNAC 2 } 


	pnacPaePortEntry OBJECT-TYPE 
		SYNTAX      PnacPaePortEntry 
		MAX-ACCESS  not-accessible 
		STATUS      current 
		DESCRIPTION 
		 "Configuration as port based or MAC based authentication 
		 and Supplicant count on a port. Index to this table is 
		 same as that of the dot1xPaePortTable, which is the 
		 InterfaceIndex." 
		INDEX { pnacPaePortNumber } 
		::= { pnacPaePortTable 1 } 

	PnacPaePortEntry ::= 
		SEQUENCE { 
		 pnacPaePortNumber 
			 InterfaceIndex, 
		 pnacPaePortAuthMode 
			 INTEGER,
		 pnacPaeMultiAuthEnable
			 INTEGER,
		  pnacPaePiggybackMode
			 INTEGER,
		  pnacPaeVlanAssignment
			 INTEGER,
		  pnacPaeSecureVlan
			 INTEGER,
		  pnacPaePortReauthenticate 
             TruthValue 	 
		} 


	pnacPaePortNumber OBJECT-TYPE 
		SYNTAX      InterfaceIndex 
		MAX-ACCESS  read-only 
		STATUS      current 
		DESCRIPTION 
		   "The port number associated with this port." 
		::= { pnacPaePortEntry 1 } 


	pnacPaePortAuthMode OBJECT-TYPE 
		SYNTAX      INTEGER { 
					   dot1x(1), 
					   macBased(2) 
				   } 
		MAX-ACCESS  read-write 
		STATUS      current 
		DESCRIPTION 
		   "Configuration of the port, for Port Based  
		   Authentication or MAC Based Authentication." 
		::= { pnacPaePortEntry 2 }

	pnacPaeMultiAuthEnable OBJECT-TYPE
	   SYNTAX      INTEGER {
					  enabled(1),
					  disabled(2)
					 }
	   MAX-ACCESS  read-write
	   STATUS      current
	   DESCRIPTION
		  "This object indicates dot1x multi hsot is enabled or disabled."
	   DEFVAL { disabled }
	   ::= { pnacPaePortEntry 3 }		    
		   
	pnacPaePiggybackMode OBJECT-TYPE
	   SYNTAX      INTEGER {
					  enabled(1),
					  disabled(2)
					 }
	   MAX-ACCESS  read-write
	   STATUS      current
	   DESCRIPTION
		  "This object indicates piggyback mode is enabled or disabled."
	   DEFVAL { disabled }
	   ::= { pnacPaePortEntry 4 }
		   
	pnacPaeVlanAssignment OBJECT-TYPE
	   SYNTAX      INTEGER {
					  enabled(1),
					  disabled(2)
					 }
	   MAX-ACCESS  read-write
	   STATUS      current
	   DESCRIPTION
		  "This object indicates vlan assignment is enabled or disabled."
	   DEFVAL { disabled }
	   ::= { pnacPaePortEntry 5 }
		   
	pnacPaeSecureVlan OBJECT-TYPE
	   SYNTAX      INTEGER {
					  enabled(1),
					  disabled(2)
					 }
	   MAX-ACCESS  read-write
	   STATUS      current
	   DESCRIPTION
		  "This object indicates Secure vlan is enabled or disabled."
	   DEFVAL { disabled }
	   ::= { pnacPaePortEntry 6}
	  
	pnacPaePortReauthenticate   OBJECT-TYPE 
		SYNTAX        TruthValue 
		MAX-ACCESS    read-write 
		STATUS        current 
		DESCRIPTION 
		   "The reauthentication control for this port. Setting 
		   this attribute TRUE causes the Authenticator PAE state 
		   machine for the Port to reauthenticate the Supplicant. 
		   Setting this attribute FALSE has no effect. 
		   This attribute always returns FALSE when it is read."
		::= { pnacPaePortEntry 7 } 
   -- --------------------------------------------------------------
   -- The Authenticator Configuration Table 
   -- --------------------------------------------------------------		
	pnacAuthConfigTable       OBJECT-TYPE 
		SYNTAX        SEQUENCE OF PnacAuthConfigEntry 
		MAX-ACCESS    not-accessible 
		STATUS        current 
		DESCRIPTION 
		   "A table that contains the configuration objects for the 
		   Authenticator PAE associated with each port. 
		   An entry appears in this table for each port that may 
		   authenticate access to itself." 
		REFERENCE 
		   "9.4.1 Authenticator Configuration" 
		::= { sysPNAC 3 } 

	pnacAuthConfigEntry       OBJECT-TYPE 
		SYNTAX        PnacAuthConfigEntry 
		MAX-ACCESS    not-accessible 
		STATUS        current 
		DESCRIPTION 
		   "The configuration information for an Authenticator 
		   PAE." 
		INDEX { pnacAuthPortNumber } 
		::= { pnacAuthConfigTable 1 } 

	PnacAuthConfigEntry ::= 
		SEQUENCE {
		  pnacAuthPortNumber
			InterfaceIndex,
		  pnacAuthPaeState 
			 INTEGER, 
		  pnacAuthAuthControlledPortStatus 
			 PaeControlledPortStatus, 
		  pnacAuthAuthControlledPortControl 
			 PaeControlledPortControl,	 
		  pnacAuthQuietPeriod 
			 Unsigned32, 
		  pnacAuthTxPeriod 
			 Unsigned32, 
		  pnacAuthSuppTimeout 
			 Unsigned32, 
		  pnacAuthServerTimeout 
			 Unsigned32, 
		  pnacAuthMaxReq 
			 Unsigned32, 
		  pnacAuthReAuthPeriod 
			 Unsigned32, 
		  pnacAuthReAuthEnabled 
			 INTEGER
		} 

	pnacAuthPortNumber       OBJECT-TYPE 
		SYNTAX        InterfaceIndex 
		MAX-ACCESS    read-only
		STATUS        current 
		DESCRIPTION 
		   "The Port number associated with this Port." 
		REFERENCE 
		   "9.6.1, Port number" 
		::= { pnacAuthConfigEntry 1 } 
			
    pnacAuthPaeState       OBJECT-TYPE 
       SYNTAX        INTEGER { 
          initialize(1), 
          disconnected(2), 
          connecting(3), 
          authenticating(4), 
          authenticated(5), 
          aborting(6), 
          held(7), 
          forceAuth(8), 
          forceUnauth(9) 
       } 
		MAX-ACCESS    read-only 
		STATUS        current 
		DESCRIPTION 
		   "The current value of the Authenticator PAE state 
		   machine." 
		REFERENCE 
		   "9.4.1, Authenticator PAE state" 
		::= { pnacAuthConfigEntry 2 } 
 
    pnacAuthAuthControlledPortStatus       OBJECT-TYPE 
		SYNTAX        PaeControlledPortStatus 
		MAX-ACCESS    read-only 
		STATUS        current 
		DESCRIPTION 
		   "The current value of the controlled Port 
		   status parameter for the Port." 
		REFERENCE 
		   "9.4.1, AuthControlledPortStatus" 
		::= { pnacAuthConfigEntry 3 } 
             
	pnacAuthAuthControlledPortControl       OBJECT-TYPE 
		SYNTAX        PaeControlledPortControl 
		MAX-ACCESS    read-write 
		STATUS        current 
		DESCRIPTION 
		   "The current value of the controlled Port 
		   control parameter for the Port." 
		REFERENCE 
		   "9.4.1, AuthControlledPortControl" 
		::= { pnacAuthConfigEntry 4 } 
	
   
	pnacAuthQuietPeriod       OBJECT-TYPE 
		SYNTAX        Unsigned32 (1..65535)
		MAX-ACCESS    read-write 
		STATUS        current 
		DESCRIPTION 
		   "The value, in seconds, of the quietPeriod constant 
		   currently in use by the Authenticator PAE state 
		   machine." 
		REFERENCE 
		   "9.4.1, quietPeriod" 
		DEFVAL { 60 } 
		::= { pnacAuthConfigEntry 5 } 
 
	pnacAuthTxPeriod       OBJECT-TYPE 
		SYNTAX        Unsigned32 (1..65535)
		MAX-ACCESS    read-write 
		STATUS        current 
		DESCRIPTION 
		   "The value, in seconds, of the txPeriod constant 
		   currently in use by the Authenticator PAE state 
		   machine." 
		REFERENCE 
		   "9.4.1, txPeriod" 
		DEFVAL { 30 } 
		::= { pnacAuthConfigEntry 6 } 
 
	pnacAuthSuppTimeout       OBJECT-TYPE 
		SYNTAX        Unsigned32  (1..65535)
		MAX-ACCESS    read-write 
		STATUS        current 
		DESCRIPTION 
		   "The value, in seconds, of the suppTimeout constant 
		   currently in use by the Backend Authentication state 
		   machine." 
		REFERENCE 
		   "9.4.1, suppTimeout" 
		DEFVAL { 30 } 
		::= { pnacAuthConfigEntry 7 } 
 
	pnacAuthServerTimeout       OBJECT-TYPE 
		SYNTAX        Unsigned32 (1..65535)
		MAX-ACCESS    read-write 
		STATUS        current 
		DESCRIPTION 
		   "The value, in seconds, of the serverTimeout constant 
		   currently in use by the Backend Authentication state 
		   machine." 
		REFERENCE 
		   "9.4.1, serverTimeout" 
		DEFVAL { 30 } 
		::= { pnacAuthConfigEntry 8 } 
 
	pnacAuthMaxReq       OBJECT-TYPE 
		SYNTAX        Unsigned32  (1..10)
		MAX-ACCESS    read-write 
		STATUS        current 
		DESCRIPTION 
		   "The value of the maxReq constant currently in use by 
		   the Backend Authentication state machine." 
		REFERENCE 
		   "9.4.1, maxReq" 
		DEFVAL { 2 } 
		::= { pnacAuthConfigEntry 9 } 
 
	pnacAuthReAuthPeriod       OBJECT-TYPE 
		SYNTAX        Unsigned32 (1..65535)
		MAX-ACCESS    read-write 
		STATUS        current 
		DESCRIPTION 
		   "The value, in seconds, of the reAuthPeriod constant 
		   currently in use by the Reauthentication Timer state 
		   machine." 
		REFERENCE 
		   "9.4.1, reAuthPeriod" 
		DEFVAL { 3600 } 
		::= { pnacAuthConfigEntry 10 } 
 
	pnacAuthReAuthEnabled       OBJECT-TYPE 
		SYNTAX      INTEGER {
                          enabled(1),
                          disabled(2)
                       }
		MAX-ACCESS    read-write 
		STATUS        current 
		DESCRIPTION 
		   "The enable/disable control used by the Reauthentication 
		   Timer state machine (8.5.5.1)." 
		REFERENCE 
		   "9.4.1, reAuthEnabled" 
		DEFVAL { disabled } 
		::= { pnacAuthConfigEntry 11 } 
		
   -- --------------------------------------------------------------
   -- The Authenticator Server Table 
   -- --------------------------------------------------------------
	pnacAuthSessionTable OBJECT-TYPE 
          SYNTAX      SEQUENCE OF PnacAuthSessionEntry 
          MAX-ACCESS  not-accessible 
          STATUS      current 
          DESCRIPTION 
             "This table contains authentication session information 
             associated with each Supplicant while Authenticator 
             operates in MAC based authentication mode." 
          ::= { sysPNAC 4 } 
 
    pnacAuthSessionEntry OBJECT-TYPE 
          SYNTAX      PnacAuthSessionEntry 
          MAX-ACCESS  not-accessible 
          STATUS      current 
          DESCRIPTION 
             "Supplicant's MAC address and session ID, states of 
             Authenticator state machine and Backend state machine 
             for the session." 
          INDEX { pnacAuthSessionSuppAddress } 
          ::= { pnacAuthSessionTable 1 } 
 
 
    PnacAuthSessionEntry ::= 
          SEQUENCE { 
             pnacAuthSessionSuppAddress 
                 MacAddress, 
             pnacAuthSessionPortNumber 
                 InterfaceIndex,
			 pnacAuthSessionPortStatus
				 InterfaceIndex
          } 
 
      pnacAuthSessionSuppAddress OBJECT-TYPE 
           SYNTAX      MacAddress 
           MAX-ACCESS  read-only
           STATUS      current 
           DESCRIPTION 
               "MAC address of the supplicant for this session." 
           ::= { pnacAuthSessionEntry 1 } 
 
      pnacAuthSessionPortNumber OBJECT-TYPE 
           SYNTAX      InterfaceIndex 
           MAX-ACCESS  read-only 
           STATUS      current 
           DESCRIPTION 
               "The Port in which this session is proceeding." 
           ::= { pnacAuthSessionEntry 2 }

      pnacAuthSessionPortStatus OBJECT-TYPE 
           SYNTAX      InterfaceIndex 
           MAX-ACCESS  read-only 
           STATUS      current 
           DESCRIPTION 
               "The Port in which this session is proceeding." 
           ::= { pnacAuthSessionEntry 3 }
		   
   -- --------------------------------------------------------------
   -- The Authenticator Server Table 
   -- --------------------------------------------------------------
   
	pnacASUserConfigTable OBJECT-TYPE
	   SYNTAX      SEQUENCE OF TabPnacASUserConfigEntry
	   MAX-ACCESS  not-accessible
	   STATUS      current
	   DESCRIPTION
		  "This table contains authentication related User
		   configuration information maintained by PNAC
		   local Authentication Server."
	   ::= { sysPNACAuthServer 1 }

	pnacASUserConfigEntry OBJECT-TYPE
	   SYNTAX      TabPnacASUserConfigEntry
	   MAX-ACCESS  not-accessible
	   STATUS      current
	   DESCRIPTION
		  "Each entry contains User name, Password, Authentication
		   protocol used, Authenticated session timeout and Access
		   ports list of the User seeking authentication."
	   INDEX { pnacASUserConfigUserName }
	   ::= { pnacASUserConfigTable 1 }

	TabPnacASUserConfigEntry ::=
	   SEQUENCE {
		  pnacASUserConfigUserName
			  SnmpAdminString,
		  pnacASUserConfigPassword
			  DisplayString,
		  pnacASUserConfigDynamicVlanID
			  Unsigned32,
		  pnacASUserConfigRowStatus
			  RowStatus
	   }

	pnacASUserConfigUserName OBJECT-TYPE
	   SYNTAX      SnmpAdminString (SIZE(1..23))
	   MAX-ACCESS  read-only
	   STATUS      current
	   DESCRIPTION
		  "Identity of the User seeking authentication. A string
		   of not more than 20 printable characters."
	   ::= { pnacASUserConfigEntry 1 }

	pnacASUserConfigPassword OBJECT-TYPE
	   SYNTAX      DisplayString   (SIZE(1..23))
	   MAX-ACCESS  read-write
	   STATUS      current
	   DESCRIPTION
		  "The secret Password of the User. A string of not
		   more than 23 printable characters.

		   When read, this always returns a String
		   of length zero."
	   ::= { pnacASUserConfigEntry 2 }

	pnacASUserConfigDynamicVlanID OBJECT-TYPE
	   SYNTAX      Unsigned32
	   MAX-ACCESS  read-write
	   STATUS      current
	   DESCRIPTION
		  "Dynamic Vlan ID is assigned by Switch in local mode"
	   ::= { pnacASUserConfigEntry 3 }

	pnacASUserConfigRowStatus OBJECT-TYPE
	   SYNTAX      RowStatus
	   MAX-ACCESS  read-create
	   STATUS      current
	   DESCRIPTION
		  "This object indicates the status of this entry. An entry is
		   created in this table when this object is SET to 'createAndWait'.
		   The entry in this table is used when the status of this object 
		   is SET 'active'. The entry in this table is not used when this 
		   object is SET 'notInService'. An entry created in this table is
		   be deleted when this object is SET 'destroy'."
	   ::= { pnacASUserConfigEntry 4 }		
		
   -- --------------------------------------------------------------
   -- The pnac VLAN List Table 
   -- --------------------------------------------------------------
   
	pnacVlanListTable OBJECT-TYPE
	   SYNTAX      SEQUENCE OF TabPnacVlanListEntry
	   MAX-ACCESS  not-accessible
	   STATUS      current
	   DESCRIPTION
		  "This table contains authentication session information
		   associated with each Guest vlan  while Authenticator
		   operates in port based authentication mode."
	   ::= { sysPNAC 5 }

	pnacVlanListEntry OBJECT-TYPE
	   SYNTAX      TabPnacVlanListEntry
	   MAX-ACCESS  not-accessible
	   STATUS      current
	   DESCRIPTION
		  "Guest Vlan ID assign with each port."
	   INDEX { pnacPortIndex }
	   ::= { pnacVlanListTable 1 }

	TabPnacVlanListEntry ::=
	   SEQUENCE {
		  pnacPortIndex
			  Integer32,
		  pnacVlanList
			  OCTET STRING

	   }

	pnacPortIndex OBJECT-TYPE
	   SYNTAX      Integer32   (1..28)
	   MAX-ACCESS  read-only
	   STATUS      current
	   DESCRIPTION
		  "The port number associated with this port."
	   ::= { pnacVlanListEntry 1 }
	   
	pnacVlanList OBJECT-TYPE
       SYNTAX     OCTET STRING (SIZE (0..512))
       MAX-ACCESS read-only
       STATUS     current
       DESCRIPTION
           "A string of octets containing one bit per VLAN. The
           first octet corresponds to VLANs with VlanId values
           1 through 8; the second octet to VLANs 9 through
           16 etc.  The most significant bit of each octet
           corresponds to the lowest VlanId value in that octet.
           This is the set of vlans configured by management to associate 
           with the management interface." 
	   ::= { pnacVlanListEntry 2}		

    privateVlanTable     OBJECT-TYPE
        SYNTAX SEQUENCE OF PrivateVlanEntry
        MAX-ACCESS not-accessible
        STATUS current
        DESCRIPTION
            "A table to control port security features of the device."
        ::= { sysPrivateVLAN 1 }
        
    privateVlanEntry OBJECT-TYPE
        SYNTAX PrivateVlanEntry
        MAX-ACCESS not-accessible
        STATUS current
        DESCRIPTION
            "An entry appears in port security table for each interface 
 	        in the system."
        INDEX { privateVlanIndex }
        ::= { privateVlanTable 1 }
  
    PrivateVlanEntry ::= 
           SEQUENCE { 
              privateVlanIndex 
                 Integer32, 
              privateVlanEgressPorts 
                 PortList           
          }
        
               
	privateVlanIndex OBJECT-TYPE 
	   SYNTAX      Integer32  (1..4094) 
	   MAX-ACCESS  read-only 
	   STATUS      current 
	   DESCRIPTION 
		  "The interface index for which the configuration in this 
		   entry applies."
	   ::= { privateVlanEntry 1 }
		   
	privateVlanEgressPorts OBJECT-TYPE
	   SYNTAX      PortList
	   MAX-ACCESS  read-create
	   STATUS      current
	   DESCRIPTION
		"The set of ports that are permanently assigned to the
		egress list for this port by management."
	   ::= { privateVlanEntry 2 }

	privateVlanState 	OBJECT-TYPE 
		SYNTAX      INTEGER {
				enabled(1),
				disabled(2)
				}
		MAX-ACCESS  read-write 
		STATUS      current 
		DESCRIPTION 
				"Enable/Disable private vlan function."
		DEFVAL  { 2 }
		::= { sysPrivateVLAN 2 } 

    
	-- Global Settings
	syslogGeneralGroup 							 OBJECT IDENTIFIER ::= { sysSyslog 1 }

	syslogTimeStamp OBJECT-TYPE 
		SYNTAX         INTEGER {
						   enabled(1),
						   disabled(2)
						  }
		MAX-ACCESS  read-write 
		STATUS      current 
		DESCRIPTION 
			"This object is for enabling or disabling timestamp option.
			When enabled, the messages (local log) will
			hold the time stamp information.
			When disabled, the time stamp information will not be carried with
			the local log."
		DEFVAL  { enabled } 
		::= { syslogGeneralGroup 1 }

	syslogSysBuffers OBJECT-TYPE 
		SYNTAX      Integer32 (1..200)
		MAX-ACCESS  read-write 
		STATUS      current 
		DESCRIPTION 
			"Number of log buffers to be allocated in the system"
		DEFVAL  { 50 }
		::= { syslogGeneralGroup 2 }

	syslogClearLog OBJECT-TYPE 
		SYNTAX         TruthValue
		MAX-ACCESS  read-write 
		STATUS      current 
		DESCRIPTION 
			"Clears the buffered logs.
				This object is set to 'false' by default. 
				When set to 'True', the buffered logs will be cleared and the value 
				of this object will become 'false' again."
		DEFVAL  { false }
		::= { syslogGeneralGroup 3 }


	-- Syslog log server configuration
	syslogLogSrv 							 OBJECT IDENTIFIER ::= { sysSyslog 2 }
	
	syslogLogSrvStatus OBJECT-TYPE
		SYNTAX       INTEGER {
						enabled(1),
						disabled(2)
					   }
		MAX-ACCESS  read-write 
		STATUS      current 
		DESCRIPTION 
			  "This object is for enabling or disabling store remote log features in syslog server."
		DEFVAL  { disabled } 
		::= { syslogLogSrv 1 }
		
	syslogLogSrvIpType OBJECT-TYPE
		SYNTAX       INTEGER{
							ipv4(1),
							ipv6(2)
						}
		MAX-ACCESS  read-write
		STATUS      current
		DESCRIPTION 
			"Specifies the syslog server IP type."
		DEFVAL { ipv4 }
		::= { syslogLogSrv 2 }
		   
	syslogLogSrvIpAddr OBJECT-TYPE
		SYNTAX		InetAddress
		MAX-ACCESS	read-write
		STATUS      current
		DESCRIPTION 
		      "Specifies the syslog server IP to be used for remote logging. When 
		      configured, a new socket will be opened for this address. 
		       When the address is changed, the socket opened for the previous address 
		       will be closed and a new socket will be opened for this address."
		::= { syslogLogSrv 3 }
		
	syslogLogSrvInterfaceName OBJECT-TYPE
	   SYNTAX      OCTET STRING (SIZE(1..32))
	   MAX-ACCESS  read-only
	   STATUS      current
	   DESCRIPTION
		   "Specifies the interface name when the syslogLogSrvIpAddr is linklocal address."
	   ::= { syslogLogSrv 4 } 

	syslogLogSrvLevel    OBJECT-TYPE
		SYNTAX		INTEGER{
						alert(0),		--For logging emergency messages.
						critical(1),	--For logging emergency messages.
						warning(2),		--For logging emergency messages.
						info(3)			--For logging emergency messages.
					}
		MAX-ACCESS	read-write
		STATUS		current
		DESCRIPTION
			"Specifies the log level option to be set for server"
		DEFVAL  { info }
		::= { syslogLogSrv 5 }

	syslogLogSrvFacility OBJECT-TYPE 
		SYNTAX		INTEGER {
						local0(128),     -- Reserved local use
						local1(136),     -- Reserved local use
						local2(144),     -- Reserved local use
						local3(152),     -- Reserved local use
						local4(160),     -- Reserved local use
						local5(168),     -- Reserved local use
						local6(176),     -- Reserved local use
						local7(184)      -- Reserved local use
					}
		MAX-ACCESS  read-write 
		STATUS      current 
		DESCRIPTION 
			"The Syslog standard facilities.
			The facility to be used when sending Syslog messages to this server."
		DEFVAL  { local0 } 
		::= { syslogLogSrv 6 }

	-- Syslog log message
	syslogLogMsg 							 OBJECT IDENTIFIER ::= { sysSyslog 3 }
	
	syslogMsgTable OBJECT-TYPE
		SYNTAX SEQUENCE OF SyslogMsgEntry
		MAX-ACCESS not-accessible
		STATUS       current
		DESCRIPTION
			"Specifies the number of messages ."
		   ::= { syslogLogMsg 1 }

	syslogMsgEntry OBJECT-TYPE
		SYNTAX     SyslogMsgEntry
		MAX-ACCESS not-accessible
		STATUS     current
		DESCRIPTION
			"An entry (conceptual row) in the syslogMsgTable."
		INDEX      { syslogMsgIndex }
		::= { syslogMsgTable 1 }

	SyslogMsgEntry ::= SEQUENCE {
			syslogMsgIndex     
				INTEGER,
			syslogMsgDescr     
				DisplayString
		}

	syslogMsgIndex OBJECT-TYPE
		SYNTAX     INTEGER (1..2147483647)
		MAX-ACCESS read-only
		STATUS     current
		DESCRIPTION
			"The auxiliary variable used for identifying instances
			of the columnar objects in the syslogMsgTable."
		::= { syslogMsgEntry 1 }

	syslogMsgDescr OBJECT-TYPE
		SYNTAX     DisplayString
		MAX-ACCESS read-only
		STATUS     current
		DESCRIPTION
			"A textual description of system log message."
		::= { syslogMsgEntry 2 }
   
	-- lldp system configuration
	lldpSystem       			OBJECT IDENTIFIER ::= { sysLLDP 1 }

	lldpSysStatus OBJECT-TYPE 
		SYNTAX		INTEGER  { 
						enabled(1), 
						disabled(2) 
					} 
		MAX-ACCESS  read-write
		STATUS      current 
		DESCRIPTION 
			"The administrative module status of LLDP module. 
			This enables or disables LLDP in the system. A value of 
			'enabled' (1) indicates that LLDP is enabled in the device
			and can be enabled port-wise. A value of 'disabled' (2) 
			indicates that LLDP is disabled in the device and also
			disabled on all ports.
             
			When LLLDP module status is changed from enabled to disabled, 
			a global timer (instead of port specific timers) is started 
			to ensure the successful transmission of shutdown frame on 
			all ports. Module status change from disabled to enabled is 
			not allowed when the global timer is running (i.e., when disable
			is in progress)."
		DEFVAL { disabled }
		::= { lldpSystem 1 }
		
	lldpMsgTxHoldMultiplier OBJECT-TYPE
		SYNTAX      Integer32(2..10)
		MAX-ACCESS  read-write
		STATUS      current
		DESCRIPTION
			"The time-to-live value expressed as a multiple of the
            lldpMessageTxInterval object.  The actual time-to-live value
            used in LLDP frames, transmitted on behalf of this LLDP agent,
            can be expressed by the following formula: TTL = min(65535,
            (lldpMessageTxInterval * lldpMessageTxHoldMultiplier)) For
            example, if the value of lldpMessageTxInterval is '30', and
            the value of lldpMessageTxHoldMultiplier is '4', then the
            value '120' is encoded in the TTL field in the LLDP header.

            The default value for lldpMessageTxHoldMultiplier object is 4.

            The value of this object must be restored from non-volatile
            storage after a re-initialization of the management system."
		REFERENCE 
            "IEEE 802.1AB-2005 10.5.3.3"
		DEFVAL { 4 }    
		::= { lldpSystem 2 }
		
	lldpMsgTxInterval OBJECT-TYPE
		SYNTAX      Integer32(5..32768)
		UNITS       "seconds"
		MAX-ACCESS  read-write
		STATUS      current
		DESCRIPTION
			"The interval at which LLDP frames are transmitted on
            behalf of this LLDP agent.

            The default value for lldpMessageTxInterval object is
            30 seconds.

            The value of this object must be restored from non-volatile
            storage after a re-initialization of the management system."
		REFERENCE 
            "IEEE 802.1AB-2005 10.5.3.3"
		DEFVAL { 30 }
		::= { lldpSystem 3 }

	lldpReinitDelay OBJECT-TYPE
		SYNTAX      Integer32(1..10)
		UNITS       "seconds"
		MAX-ACCESS  read-write
		STATUS      current
		DESCRIPTION
            "The cuslldpReinitDelay indicates the delay (in units of
            seconds) from when cuslldpPortConfigAdminStatus object of a
            particular port becomes 'disabled' until re-initialization
            will be attempted.

            The default value for cuslldpReintDelay object is two seconds.

            The value of this object must be restored from non-volatile
            storage after a re-initialization of the management system."
		REFERENCE 
            "IEEE 802.1AB-2005 10.5.3.3"
		DEFVAL { 2 }    
		::= { lldpSystem 4 }

	lldpTxDelay OBJECT-TYPE
		SYNTAX      Integer32(1..8192)
		UNITS       "seconds"
		MAX-ACCESS  read-write
		STATUS      current
		DESCRIPTION
            "The lldpTxDelay indicates the delay (in units
            of seconds) between successive LLDP frame transmissions 
            initiated by value/status changes in the LLDP local systems
            MIB.  The recommended value for the lldpTxDelay is set by the
            following  formula:

               1 <= lldpTxDelay <= (0.25 * lldpMsgTxInterval)

            The default value for lldpTxDelay object is two seconds.

            The value of this object must be restored from non-volatile
            storage after a re-initialization of the management system."
		REFERENCE 
            "IEEE 802.1AB-2005 10.5.3.3"
		DEFVAL { 2 }    
		::= { lldpSystem 5}   
    
	-- lldp port configuration 
	lldpPortConfigTable   OBJECT-TYPE
		SYNTAX      SEQUENCE OF LLDPPortConfigEntry
		MAX-ACCESS  not-accessible
		STATUS      current
		DESCRIPTION
            "The table that controls LLDP frame transmission on individual
            ports."
    ::= { lldpSystem 6 }

	lldpPortConfigEntry   OBJECT-TYPE
		SYNTAX      LLDPPortConfigEntry
		MAX-ACCESS  not-accessible
		STATUS      current
		DESCRIPTION
            "LLDP configuration information for a particular port.
            This configuration parameter controls the transmission and
            the reception of LLDP frames on those ports whose rows are
            created in this table."
		INDEX  { lldpPortConfigPortNum }
		::= { lldpPortConfigTable 1 }

	LLDPPortConfigEntry ::= 
		SEQUENCE {
			lldpPortConfigPortNum
				LldpPortNumber,
			lldpPortConfigAdminStatus
				INTEGER
			}

	lldpPortConfigPortNum   OBJECT-TYPE
		SYNTAX      LldpPortNumber 
		MAX-ACCESS  read-only
		STATUS      current
		DESCRIPTION
			"The index value used to identify the port component
            (contained in the local chassis with the LLDP agent)
            associated with this entry.

            The value of this object is used as a port index to the
			lldpPortConfigTable."
		::= { lldpPortConfigEntry 1 }

	lldpPortConfigAdminStatus  OBJECT-TYPE 
		SYNTAX	INTEGER { 
					txOnly(1), 
					rxOnly(2),
					txAndRx(3),
					disabled(4)
				}
		MAX-ACCESS read-write 
		STATUS     current 
		DESCRIPTION 
            "The administratively desired status of the local LLDP agent.

            If the associated cuslldpPortConfigAdminStatus object has a
            value of 'txOnly(1)', then LLDP agent will transmit LLDP
            frames on this port and it will not store any information
            about the remote systems connected.
         
            If the associated cuslldpPortConfigAdminStatus object has a
            value of 'rxOnly(2)', then the LLDP agent will receive,
            but it will not transmit LLDP frames on this port.

            If the associated cuslldpPortConfigAdminStatus object has a
            value of 'txAndRx(3)', then the LLDP agent will transmit
            and receive LLDP frames on this port.

            If the associated cuslldpPortConfigAdminStatus object has a
            value of 'disabled(4)', then LLDP agent will not transmit or
            receive LLDP frames on this port.  If there is remote systems
            information which is received on this port and stored in
            other tables, before the port's cuslldpPortConfigAdminStatus
            becomes disabled, then the information will naturally age out."
		REFERENCE 
            "IEEE 802.1AB-2005 10.5.1"
		DEFVAL  { txAndRx }    
		::= { lldpPortConfigEntry 2 }

		
	-- lldp local system data
	lldpLocalData     			OBJECT IDENTIFIER ::= { sysLLDP 2 } 
		
	lldpLocChassisIdSubtype  OBJECT-TYPE
		SYNTAX      LldpChassisIdSubtype
		MAX-ACCESS  read-only
		STATUS      current
		DESCRIPTION
            "The type of encoding used to identify the chassis
            associated with the local system."
		REFERENCE 
            "IEEE 802.1AB-2005 9.5.2.2"
		::= { lldpLocalData 1 }

	lldpLocChassisId  OBJECT-TYPE
		SYNTAX      LldpChassisId
		MAX-ACCESS  read-only
		STATUS      current
		DESCRIPTION
            "The string value used to identify the chassis component
            associated with the local system."
		REFERENCE 
            "IEEE 802.1AB-2005 9.5.2.3"
		::= { lldpLocalData 2 }

	lldpLocSysName  OBJECT-TYPE
		SYNTAX      SnmpAdminString (SIZE(0..255))
		MAX-ACCESS  read-only
		STATUS      current
		DESCRIPTION
            "The string value used to identify the system name of the
            local system.  If the local agent supports IETF RFC 3418,
            cuslldpLocSysName object should have the same value of sysName
            object."
		REFERENCE 
            "IEEE 802.1AB-2005 9.5.6.2"
		::= { lldpLocalData 3 }

	lldpLocSysDesc  OBJECT-TYPE
		SYNTAX      SnmpAdminString (SIZE(0..255))
		MAX-ACCESS  read-only
		STATUS      current
		DESCRIPTION
            "The string value used to identify the system description
            of the local system.  If the local agent supports IETF RFC 3418,
            cuslldpLocSysDesc object should have the same value of sysDesc
            object."
		REFERENCE 
            "IEEE 802.1AB-2005 9.5.7.2"
		::= { lldpLocalData 4 }


	-- lldp remote system data
	lldpRemoteData   			OBJECT IDENTIFIER ::= { sysLLDP 3 }

	lldpRemTable OBJECT-TYPE
		SYNTAX      SEQUENCE OF LldpRemEntry
		MAX-ACCESS  not-accessible
		STATUS      current
		DESCRIPTION
				"This table contains one or more rows per physical network
				connection known to this agent.  The agent may wish to ensure
				that only one lldpRemEntry is present for each local port,
				or it may choose to maintain multiple lldpRemEntries for
				the same local port."
		::= { lldpRemoteData 1 }

	lldpRemEntry OBJECT-TYPE
		SYNTAX      LldpRemEntry
		MAX-ACCESS  not-accessible
		STATUS      current
		DESCRIPTION
				"Information about a particular physical network connection.
				Entries may be created and deleted in this table by the agent,
				if a physical topology discovery process is active."
		INDEX   {
			   lldpRemTimeMark,
			   lldpRemLocalPortNum,
			   lldpRemIndex
		}
		::= { lldpRemTable 1 }

	LldpRemEntry ::= SEQUENCE {
		  lldpRemTimeMark           			TimeFilter,
		  lldpRemLocalPortNum       			LldpPortNumber,
		  lldpRemIndex              			Integer32,
		  lldpRemChassisIdSubtype   			LldpChassisIdSubtype,
		  lldpRemChassisId          			LldpChassisId,
		  lldpRemPortIdSubtype      			LldpPortIdSubtype,
		  lldpRemPortId             			LldpPortId,
		  lldpRemPortDesc           			SnmpAdminString,
		  lldpRemSysName            			SnmpAdminString,
		  lldpRemSysDesc						SnmpAdminString,
		  lldpRemSysCapSupported				LldpSystemCapabilitiesMap,
		  lldpRemSysCapEnabled					LldpSystemCapabilitiesMap,
		  lldpRemPortVlanId						Integer32,
		  lldpRemPortAutoNegSupported			TruthValue,
		  lldpRemPortAutoNegEnabled				TruthValue,
		  lldpRemPortAutoNegAdvertisedCap		OCTET STRING,
		  lldpRemLinkAggStatus       			LldpLinkAggStatusMap,
		  lldpRemMaxFrameSize					Integer32,
		  
		  lldpMedRemCapSupported     			LldpXMedCapabilities,
		  lldpMedRemHardwareRev           		SnmpAdminString,
          lldpMedRemFirmwareRev           		SnmpAdminString,
          lldpMedRemSoftwareRev           		SnmpAdminString,
          lldpMedRemSerialNum             		SnmpAdminString,
          lldpMedRemMfgName               		SnmpAdminString,
          lldpMedRemModelName             		SnmpAdminString,
          lldpMedRemAssetID               		SnmpAdminString
	}

	lldpRemTimeMark  OBJECT-TYPE
		SYNTAX      TimeFilter
		MAX-ACCESS  read-only
		STATUS      current
		DESCRIPTION
				"A TimeFilter for this entry.  See the TimeFilter textual
				convention in IETF RFC 2021 and 
				http://www.ietf.org/IESG/Implementations/RFC2021-Implementation.txt
				to see how TimeFilter works."
		REFERENCE 
				"IETF RFC 2021 section 6"
		::= { lldpRemEntry 1 }

	lldpRemLocalPortNum  OBJECT-TYPE
		SYNTAX      LldpPortNumber
		MAX-ACCESS  read-only
		STATUS      current
		DESCRIPTION
				"The index value used to identify the port component
				(contained in the local chassis with the LLDP agent)
				associated with this entry.  The lldpRemLocalPortNum
				identifies the port on which the remote system information
				is received.

				The value of this object is used as a port index to the
				lldpRemTable."
		::= { lldpRemEntry 2 }

	lldpRemIndex  OBJECT-TYPE
		SYNTAX      Integer32(1..2147483647)
		MAX-ACCESS  read-only
		STATUS      current
		DESCRIPTION
				"This object represents an arbitrary local integer value used
				by this agent to identify a particular connection instance,
				unique only for the indicated remote system.

				An agent is encouraged to assign monotonically increasing
				index values to new entries, starting with one, after each
				reboot.  It is considered unlikely that the lldpRemIndex
				will wrap between reboots."
		::= { lldpRemEntry 3 }

	lldpRemChassisIdSubtype  OBJECT-TYPE
		SYNTAX      LldpChassisIdSubtype
		MAX-ACCESS  read-only
		STATUS      current
		DESCRIPTION
				"The type of encoding used to identify the chassis associated
				with the remote system."
		REFERENCE 
				"IEEE 802.1AB-2005 9.5.2.2"
		::= { lldpRemEntry 4 }

	lldpRemChassisId  OBJECT-TYPE
		SYNTAX      LldpChassisId
		MAX-ACCESS  read-only
		STATUS      current
		DESCRIPTION
				"The string value used to identify the chassis component
				associated with the remote system."
		REFERENCE 
				"IEEE 802.1AB-2005 9.5.2.3"
		::= { lldpRemEntry 5 }

	lldpRemPortIdSubtype  OBJECT-TYPE
		SYNTAX      LldpPortIdSubtype
		MAX-ACCESS  read-only
		STATUS      current
		DESCRIPTION
				"The type of port identifier encoding used in the associated
				'lldpRemPortId' object."
		REFERENCE 
				"IEEE 802.1AB-2005 9.5.3.2"
		::= { lldpRemEntry 6 }

	lldpRemPortId  OBJECT-TYPE
		SYNTAX      LldpPortId
		MAX-ACCESS  read-only
		STATUS      current
		DESCRIPTION
				"The string value used to identify the port component
				associated with the remote system."
		REFERENCE 
				"IEEE 802.1AB-2005 9.5.3.3"
		::= { lldpRemEntry 7 }

	lldpRemPortDesc  OBJECT-TYPE
		SYNTAX      SnmpAdminString (SIZE(0..255))
		MAX-ACCESS  read-only
		STATUS      current
		DESCRIPTION
				"The string value used to identify the description of
				the given port associated with the remote system."
		REFERENCE 
				"IEEE 802.1AB-2005 9.5.5.2"
		::= { lldpRemEntry 8 }

	lldpRemSysName  OBJECT-TYPE
		SYNTAX      SnmpAdminString (SIZE(0..255))
		MAX-ACCESS  read-only
		STATUS      current
		DESCRIPTION
				"The string value used to identify the system name of the
				remote system."
		REFERENCE 
				"IEEE 802.1AB-2005 9.5.6.2"
		::= { lldpRemEntry 9 }

	lldpRemSysDesc  OBJECT-TYPE
		SYNTAX      SnmpAdminString (SIZE(0..255))
		MAX-ACCESS  read-only
		STATUS      current
		DESCRIPTION
				"The string value used to identify the system description
				of the remote system."
		REFERENCE 
				"IEEE 802.1AB-2005 9.5.7.2"
		::= { lldpRemEntry 10 }

	lldpRemSysCapSupported OBJECT-TYPE
		SYNTAX      LldpSystemCapabilitiesMap
		MAX-ACCESS  read-only
		STATUS      current
		DESCRIPTION
				"The bitmap value used to identify which system capabilities
				are supported on the remote system."
		REFERENCE 
				"IEEE 802.1AB-2005 9.5.8.1"
		::= { lldpRemEntry 11 }

	lldpRemSysCapEnabled  OBJECT-TYPE
		SYNTAX      LldpSystemCapabilitiesMap
		MAX-ACCESS  read-only
		STATUS      current
		DESCRIPTION
				"The bitmap value used to identify which system capabilities
				are enabled on the remote system."
		REFERENCE 
				"IEEE 802.1AB-2005 9.5.8.2"
		::= { lldpRemEntry 12 }

	-- XDot1 port vlan id 
	lldpRemPortVlanId OBJECT-TYPE
		SYNTAX      Integer32(0|1..4094)
		MAX-ACCESS  read-only
		STATUS      current
		DESCRIPTION
				"The integer value used to identify the port's VLAN identifier
				associated with the remote system.  if the remote system
				either does not know the PVID or does not support port-based
				VLAN operation, the value of lldpXdot1RemPortVlanId should
				be zero."
		REFERENCE 
				"IEEE 802.1AB-2005 F.2.1"
		::= { lldpRemEntry 13 }
		
	-- Xdot3 
	lldpRemPortAutoNegSupported OBJECT-TYPE
		SYNTAX      TruthValue
		MAX-ACCESS  read-only
		STATUS      current
		DESCRIPTION
				"The truth value used to indicate whether the given port
				(associated with remote system) supports Auto-negotiation."
		REFERENCE 
				"IEEE 802.1AB-2005 G.2.1"
		::= { lldpRemEntry 14 }

	lldpRemPortAutoNegEnabled  OBJECT-TYPE
		SYNTAX      TruthValue
		MAX-ACCESS  read-only
		STATUS      current
		DESCRIPTION
				"The truth value used to indicate whether port
				Auto-negotiation is enabled on the given port associated
				with the remote system."
		REFERENCE 
				"IEEE 802.1AB-2005 G.2.1"
		::= { lldpRemEntry 15 }

	lldpRemPortAutoNegAdvertisedCap  OBJECT-TYPE
		SYNTAX      OCTET STRING(SIZE(2))
		MAX-ACCESS  read-only
		STATUS      current
		DESCRIPTION
				"This object contains the value (bitmap) of the
				ifMauAutoNegCapAdvertisedBits object (defined in IETF RFC
				3636) which is associated with the given port on the
				remote system."
		REFERENCE 
				"IEEE 802.1AB-2005 G.2.2"
		::= { lldpRemEntry 16 }

	lldpRemLinkAggStatus OBJECT-TYPE
		SYNTAX      LldpLinkAggStatusMap
		MAX-ACCESS  read-only
		STATUS      current
		DESCRIPTION
				"The bitmap value contains the link aggregation capabilities
				and the current aggregation status of the link."
		REFERENCE 
				"IEEE 802.1AB-2005 G.4.1"
		::= { lldpRemEntry 17 }

	lldpRemMaxFrameSize OBJECT-TYPE
		SYNTAX      Integer32(0..65535)
		MAX-ACCESS  read-only
		STATUS      current
		DESCRIPTION
				"An integer value indicating the maximum supported frame 
				 size in octets on the port component associated with the 
				 remote system."
		REFERENCE 
				"IEEE 802.1AB-2005 G.5.2"
		::= { lldpRemEntry 18 }
		
   --Med
	lldpMedRemCapSupported  OBJECT-TYPE
        SYNTAX      LldpXMedCapabilities
        MAX-ACCESS  read-only
        STATUS      current
        DESCRIPTION
                "The bitmap includes the MED organizationally defined set of LLDP
                TLVs whose transmission is possible on the LLDP agent of the remote
                device connected to this port. Each bit in the bitmap corresponds
                to an LLDP-MED subtype associated with a specific TIA TR41.4 MED
                optional TLV. If the bit is set, the agent has the capability
                to support the corresponding TLV."
        REFERENCE
                "ANSI/TIA-1057, Sections 10.2.2.1"
    ::= { lldpRemEntry  19 }
    lldpMedRemHardwareRev    OBJECT-TYPE
        SYNTAX      SnmpAdminString (SIZE (0..32))
        MAX-ACCESS  read-only
        STATUS      current
        DESCRIPTION
                "The vendor-specific hardware revision string
                as advertised by the remote endpoint."
        REFERENCE
                " ANSI/TIA-1057, Section 10.2.6.1"
        ::= { lldpRemEntry 20 }

    lldpMedRemFirmwareRev    OBJECT-TYPE
        SYNTAX      SnmpAdminString (SIZE (0..32))
        MAX-ACCESS  read-only
        STATUS      current
        DESCRIPTION
                "The vendor-specific firmware revision string
                as advertised by the remote endpoint."
        REFERENCE
                " ANSI/TIA-1057, Section 10.2.6.2"
        ::= { lldpRemEntry 21 }

    lldpMedRemSoftwareRev    OBJECT-TYPE
        SYNTAX      SnmpAdminString (SIZE (0..32))
        MAX-ACCESS  read-only
        STATUS      current
        DESCRIPTION
                "The vendor-specific software revision string
                as advertised by the remote endpoint."
        REFERENCE
                " ANSI/TIA-1057, Section 10.2.6.3"
        ::= { lldpRemEntry 22 }

    lldpMedRemSerialNum    OBJECT-TYPE
        SYNTAX      SnmpAdminString (SIZE (0..32))
        MAX-ACCESS  read-only
        STATUS      current
        DESCRIPTION
                "The vendor-specific serial number
                as advertised by the remote endpoint."
        REFERENCE
                " ANSI/TIA-1057, Section 10.2.6.4"
        ::= { lldpRemEntry 23 }

    lldpMedRemMfgName    OBJECT-TYPE
        SYNTAX      SnmpAdminString (SIZE (0..32))
        MAX-ACCESS  read-only
        STATUS      current
        DESCRIPTION
                "The vendor-specific manufacturer name
                as advertised by the remote endpoint."
        REFERENCE
                " ANSI/TIA-1057, Section 10.2.6.5"
        ::= { lldpRemEntry 24 }

    lldpMedRemModelName    OBJECT-TYPE
        SYNTAX      SnmpAdminString (SIZE (0..32))
        MAX-ACCESS  read-only
        STATUS      current
        DESCRIPTION
                "The vendor-specific model name
                as advertised by the remote endpoint."
        REFERENCE
                " ANSI/TIA-1057, Section 10.2.6.6"
        ::= { lldpRemEntry 25 }

    lldpMedRemAssetID    OBJECT-TYPE
        SYNTAX      SnmpAdminString (SIZE (0..32))
        MAX-ACCESS  read-only
        STATUS      current
        DESCRIPTION
                "The vendor-specific asset tracking identifier
                as advertised by the remote endpoint."
        REFERENCE
                " ANSI/TIA-1057, Section 10.2.6.7"
        ::= { lldpRemEntry 26 } 
      
--
-- lldpRemManTable : Management addresses of the remote system
--

lldpRemManTable OBJECT-TYPE
    SYNTAX      SEQUENCE OF LldpRemManEntry
    MAX-ACCESS  not-accessible
    STATUS      current
    DESCRIPTION
            "This table contains one or more rows per management address
            information on the remote system learned on a particular port
            contained in the local chassis known to this agent."
    ::= { lldpRemoteData 2 }

lldpRemManEntry OBJECT-TYPE
    SYNTAX      LldpRemManEntry
    MAX-ACCESS  not-accessible
    STATUS      current
    DESCRIPTION
            "Management address information about a particular chassis
            component.  There may be multiple management addresses
            configured on the remote system identified by a particular
            lldpRemIndex whose information is received on
            lldpRemLocalPortNum of the local system.  Each management
            address should have distinct 'management address
            type' (lldpRemManAddrSubtype) and 'management address'
            (lldpRemManAddr.)

            Entries may be created and deleted in this table by the
            agent."
    INDEX   { lldpRemManTimeMark,
              lldpRemManLocalPortNum,
              lldpRemManIndex,
              lldpRemManAddrSubtype,
              lldpRemManAddr
			}
    ::= { lldpRemManTable 1 }

LldpRemManEntry ::= SEQUENCE {
      lldpRemManTimeMark        TimeFilter,
      lldpRemManLocalPortNum    LldpPortNumber,
      lldpRemManIndex           Integer32,
      lldpRemManAddrSubtype     AddressFamilyNumbers,
      lldpRemManAddr            LldpManAddress,
      lldpRemManAddrIfSubtype   LldpManAddrIfSubtype,
      lldpRemManAddrIfId        Integer32
}

lldpRemManTimeMark  OBJECT-TYPE
    SYNTAX      TimeFilter
    MAX-ACCESS  read-only
    STATUS      current
    DESCRIPTION
            "A TimeFilter for this entry.  See the TimeFilter textual
            convention in IETF RFC 2021 and 
            http://www.ietf.org/IESG/Implementations/RFC2021-Implementation.txt
            to see how TimeFilter works."
    REFERENCE 
            "IETF RFC 2021 section 6"
    ::= { lldpRemManEntry 1 }

lldpRemManLocalPortNum  OBJECT-TYPE
    SYNTAX      LldpPortNumber
    MAX-ACCESS  read-only
    STATUS      current
    DESCRIPTION
            "The index value used to identify the port component
            (contained in the local chassis with the LLDP agent)
            associated with this entry.  The lldpRemLocalPortNum
            identifies the port on which the remote system information
            is received.

            The value of this object is used as a port index to the
            lldpRemTable."
    ::= { lldpRemManEntry 2 }

lldpRemManIndex  OBJECT-TYPE
    SYNTAX      Integer32(1..2147483647)
    MAX-ACCESS  read-only
    STATUS      current
    DESCRIPTION
            "This object represents an arbitrary local integer value used
            by this agent to identify a particular connection instance,
            unique only for the indicated remote system.

            An agent is encouraged to assign monotonically increasing
            index values to new entries, starting with one, after each
            reboot.  It is considered unlikely that the lldpRemIndex
            will wrap between reboots."
    ::= { lldpRemManEntry 3 }

lldpRemManAddrSubtype  OBJECT-TYPE
    SYNTAX      AddressFamilyNumbers
    MAX-ACCESS  read-only
    STATUS      current
    DESCRIPTION
            "The type of management address identifier encoding used in
            the associated 'lldpRemManagmentAddr' object."
    REFERENCE 
            "IEEE 802.1AB-2005 9.5.9.3"
    ::= { lldpRemManEntry 4 }

lldpRemManAddr  OBJECT-TYPE
    SYNTAX      LldpManAddress
    MAX-ACCESS  read-only
    STATUS      current
    DESCRIPTION
            "The string value used to identify the management address
            component associated with the remote system.  The purpose
            of this address is to contact the management entity."
    REFERENCE 
            "IEEE 802.1AB-2005 9.5.9.4"
    ::= { lldpRemManEntry 5 }

lldpRemManAddrIfSubtype  OBJECT-TYPE
    SYNTAX      LldpManAddrIfSubtype
    MAX-ACCESS  read-only
    STATUS      current
    DESCRIPTION
            "The enumeration value that identifies the interface numbering
            method used for defining the interface number, associated
            with the remote system."
    REFERENCE 
            "IEEE 802.1AB-2005 9.5.9.5"
    ::= { lldpRemManEntry 6 }

lldpRemManAddrIfId  OBJECT-TYPE
    SYNTAX      Integer32
    MAX-ACCESS  read-only
    STATUS      current
    DESCRIPTION
            "The integer value used to identify the interface number
            regarding the management address component associated with
            the remote system."
    REFERENCE 
            "IEEE 802.1AB-2005 9.5.9.6"
    ::= { lldpRemManEntry 7 }

-- 
-- lldpRemVlanTable : VLAN name information of the remote systems
--

lldpRemVlanTable  OBJECT-TYPE
    SYNTAX      SEQUENCE OF LldpRemVlanEntry
    MAX-ACCESS  not-accessible
    STATUS      current
    DESCRIPTION
            "This table contains one or more rows per IEEE 802.1Q VLAN
            name information about the remote system, received on the
            given port."
    REFERENCE 
            "IEEE 802.1AB-2005 F.4"
    ::= { lldpRemoteData 3 }

lldpRemVlanEntry OBJECT-TYPE
    SYNTAX      LldpRemVlanEntry 
    MAX-ACCESS  not-accessible
    STATUS      current
    DESCRIPTION
            "VLAN name Information about a particular port component.
            There may be multiple VLANs, identified by a particular
            lldpXdot1RemVlanId, received on the given port."
    INDEX   { lldpRemVlanTimeMark,
              lldpRemVlanLocalPortNum,
              lldpRemVlanIndex,
              lldpRemVlanId 
			 }
    ::= { lldpRemVlanTable 1 }

LldpRemVlanEntry ::= SEQUENCE {
      lldpRemVlanTimeMark       TimeFilter,
      lldpRemVlanLocalPortNum   LldpPortNumber,
      lldpRemVlanIndex          Integer32,
      lldpRemVlanId     		VlanId,
      lldpRemVlanName   		SnmpAdminString
}

lldpRemVlanTimeMark  OBJECT-TYPE
    SYNTAX      TimeFilter
    MAX-ACCESS  read-only
    STATUS      current
    DESCRIPTION
            "A TimeFilter for this entry.  See the TimeFilter textual
            convention in IETF RFC 2021 and 
            http://www.ietf.org/IESG/Implementations/RFC2021-Implementation.txt
            to see how TimeFilter works."
    REFERENCE 
            "IETF RFC 2021 section 6"
    ::= { lldpRemVlanEntry 1 }

lldpRemVlanLocalPortNum  OBJECT-TYPE
    SYNTAX      LldpPortNumber
    MAX-ACCESS  read-only
    STATUS      current
    DESCRIPTION
            "The index value used to identify the port component
            (contained in the local chassis with the LLDP agent)
            associated with this entry.  The lldpRemLocalPortNum
            identifies the port on which the remote system information
            is received.

            The value of this object is used as a port index to the
            lldpRemTable."
    ::= { lldpRemVlanEntry 2 }

lldpRemVlanIndex  OBJECT-TYPE
    SYNTAX      Integer32(1..2147483647)
    MAX-ACCESS  read-only
    STATUS      current
    DESCRIPTION
            "This object represents an arbitrary local integer value used
            by this agent to identify a particular connection instance,
            unique only for the indicated remote system.

            An agent is encouraged to assign monotonically increasing
            index values to new entries, starting with one, after each
            reboot.  It is considered unlikely that the lldpRemIndex
            will wrap between reboots."
    ::= { lldpRemVlanEntry 3 }

lldpRemVlanId  OBJECT-TYPE
    SYNTAX      VlanId
    MAX-ACCESS  read-only
    STATUS      current
    DESCRIPTION
            "The integer value used to identify the IEEE 802.1Q 
            VLAN IDs with which the given port of the remote system
            is compatible."
    REFERENCE 
            "IEEE 802.1AB-2005 F.4.2"
    ::= { lldpRemVlanEntry 4 }

lldpRemVlanName  OBJECT-TYPE
    SYNTAX      SnmpAdminString (SIZE(1..32))
    MAX-ACCESS  read-only
    STATUS      current
    DESCRIPTION
            "The string value used to identify VLAN name identified by the 
            VLAN Id associated with the remote system."
    REFERENCE 
            "IEEE 802.1AB-2005 F.4.4"
    ::= { lldpRemVlanEntry 5 }
	
--
-- lldpRemProtoTable: Remote Port and Protocol VLAN information 
--

lldpRemProtoTable  OBJECT-TYPE
    SYNTAX      SEQUENCE OF LldpRemProtoEntry
    MAX-ACCESS  not-accessible
    STATUS      current
    DESCRIPTION
            "This table contains one or more rows per Port and Protocol
            VLAN information about the remote system, received on the
            given port."
    ::= { lldpRemoteData 4 }

lldpRemProtoEntry OBJECT-TYPE
    SYNTAX      LldpRemProtoEntry 
    MAX-ACCESS  not-accessible
    STATUS      current
    DESCRIPTION
            "Port and protocol VLAN name Information about a particular
            port component.  There may be multiple protocol VLANs,
            identified by a particular lldpXdot1RemProtoVlanId, configured
            on the remote system."
    INDEX   { lldpRemProtoTimeMark,
              lldpRemProtoLocPortNum,
              lldpRemProtoIndex,
              lldpRemProtoVlanId }
    ::= { lldpRemProtoTable 1 }

LldpRemProtoEntry ::= SEQUENCE {
      lldpRemProtoTimeMark      TimeFilter,
      lldpRemProtoLocPortNum   	LldpPortNumber,
      lldpRemProtoIndex         Integer32,
      lldpRemProtoVlanId        Integer32,
      lldpRemProtoVlanSupported TruthValue,
      lldpRemProtoVlanEnabled   TruthValue
}

lldpRemProtoTimeMark  OBJECT-TYPE
    SYNTAX      TimeFilter
    MAX-ACCESS  read-only
    STATUS      current
    DESCRIPTION
            "A TimeFilter for this entry.  See the TimeFilter textual
            convention in IETF RFC 2021 and 
            http://www.ietf.org/IESG/Implementations/RFC2021-Implementation.txt
            to see how TimeFilter works."
    REFERENCE 
            "IETF RFC 2021 section 6"
    ::= { lldpRemProtoEntry 1 }

lldpRemProtoLocPortNum  OBJECT-TYPE
    SYNTAX      LldpPortNumber
    MAX-ACCESS  read-only
    STATUS      current
    DESCRIPTION
            "The index value used to identify the port component
            (contained in the local chassis with the LLDP agent)
            associated with this entry.  The lldpRemLocalPortNum
            identifies the port on which the remote system information
            is received.

            The value of this object is used as a port index to the
            lldpRemTable."
    ::= { lldpRemProtoEntry 2 }

lldpRemProtoIndex  OBJECT-TYPE
    SYNTAX      Integer32(1..2147483647)
    MAX-ACCESS  read-only
    STATUS      current
    DESCRIPTION
            "This object represents an arbitrary local integer value used
            by this agent to identify a particular connection instance,
            unique only for the indicated remote system.

            An agent is encouraged to assign monotonically increasing
            index values to new entries, starting with one, after each
            reboot.  It is considered unlikely that the lldpRemIndex
            will wrap between reboots."
    ::= { lldpRemProtoEntry 3 }

lldpRemProtoVlanId  OBJECT-TYPE
    SYNTAX      Integer32(0|1..4094)
    MAX-ACCESS  read-only
    STATUS      current
    DESCRIPTION
            "The integer value used to identify the port and protocol
            VLANs associated with the given port associated with the
            remote system.

            If port and protocol VLANs are not supported on the given
            port associated with the remote system, or if the port is
            not enabled with any port and protocol VLAN, the value of
            lldpXdot1RemProtoVlanId should be zero."
    REFERENCE 
            "IEEE 802.1AB-2005 F.3.2"
    ::= { lldpRemProtoEntry 4 }

lldpRemProtoVlanSupported  OBJECT-TYPE
    SYNTAX      TruthValue
    MAX-ACCESS  read-only
    STATUS      current
    DESCRIPTION
            "The truth value used to indicate whether the given port
            (associated with the remote system) is capable of supporting
            port and protocol VLANs."
    REFERENCE 
            "IEEE 802.1AB-2005 F.3.1"
    ::= { lldpRemProtoEntry 5 }

lldpRemProtoVlanEnabled  OBJECT-TYPE
    SYNTAX      TruthValue
    MAX-ACCESS  read-only
    STATUS      current
    DESCRIPTION
            "The truth value used to indicate whether the port and
            protocol VLANs are enabled on the given port associated with
            the remote system."
    REFERENCE 
            "IEEE 802.1AB-2005 F.3.1"
    ::= { lldpRemProtoEntry 6 } 
    
 --- lldpMedRemMediaPolicyTable: Media Policy Table
---
---
    lldpMedRemMediaPolicyTable OBJECT-TYPE
        SYNTAX      SEQUENCE OF LldpMedRemMediaPolicyEntry
        MAX-ACCESS  not-accessible
        STATUS      current
        DESCRIPTION
                "This table contains media policy information as advertised
                by the remote system.

                This table may be sparsely populated. Entries in this table are
                relevant only if the networkPolicy(0) bits in the
                lldpXMedRemCapSupported and lldpXMedRemCapCurrent objects of the
                corresponding ports are set."
        ::= { lldpRemoteData 5 }

    lldpMedRemMediaPolicyEntry OBJECT-TYPE
        SYNTAX      LldpMedRemMediaPolicyEntry
        MAX-ACCESS  not-accessible
        STATUS      current
        DESCRIPTION
                "Information about the per port per policy type policy
                 information for a particular physical network connection."
        INDEX   { lldpMedRemMediaPolicyTimeMark,
                  lldpMedRemMediaPolicyPortNum,
                  lldpMedRemMediaPolicyIndex,
                  lldpMedRemMediaPolicyAppType }
        ::= { lldpMedRemMediaPolicyTable 1 }


    LldpMedRemMediaPolicyEntry ::= SEQUENCE {
            lldpMedRemMediaPolicyTimeMark       TimeFilter,
            lldpMedRemMediaPolicyPortNum        LldpPortNumber,
            lldpMedRemMediaPolicyIndex          Integer32,
            lldpMedRemMediaPolicyAppType        PolicyAppType,
            lldpMedRemMediaPolicyVlanID         Integer32,
            lldpMedRemMediaPolicyPriority       Integer32,
            lldpMedRemMediaPolicyDscp           Dscp,
            lldpMedRemMediaPolicyUnknown        TruthValue,
            lldpMedRemMediaPolicyTagged         TruthValue
    }

lldpMedRemMediaPolicyTimeMark  OBJECT-TYPE
        SYNTAX      TimeFilter
        MAX-ACCESS  read-only
        STATUS      current
        DESCRIPTION
                "A TimeFilter for this entry.  See the TimeFilter textual
                convention in IETF RFC 2021 and
                http://www.ietf.org/IESG/Implementations/RFC2021-Implementation.txt
                to see how TimeFilter works."
        REFERENCE
                "IETF RFC 2021 section 6"
    ::= { lldpMedRemMediaPolicyEntry 1 }

lldpMedRemMediaPolicyPortNum  OBJECT-TYPE
            SYNTAX      LldpPortNumber
            MAX-ACCESS  read-only
            STATUS      current
            DESCRIPTION
                    "The index value used to identify the port component
                    (contained in the local chassis with the LLDP agent)
                    associated with this entry.
        
                    The value of this object is used as a port index to the
                    lldpLocPortTable."
        ::= { lldpMedRemMediaPolicyEntry 2 }
        
lldpMedRemMediaPolicyIndex  OBJECT-TYPE
        SYNTAX      Integer32(1..2147483647)
        MAX-ACCESS  read-only
        STATUS      current
        DESCRIPTION
                "This object represents an arbitrary local integer value used
                by this agent to identify a particular connection instance,
                unique only for the indicated remote system.
    
                An agent is encouraged to assign monotonically increasing
                index values to new entries, starting with one, after each
                reboot.  It is considered unlikely that the lldpRemIndex
                will wrap between reboots."
    ::= { lldpMedRemMediaPolicyEntry 3 }
    
    lldpMedRemMediaPolicyAppType OBJECT-TYPE
        SYNTAX      PolicyAppType
        MAX-ACCESS  read-only
        STATUS      current
        DESCRIPTION
                "The media type that defines the primary function of the
                 application for the policy advertised by the endpoint connected
                 remotely to this port."
        REFERENCE
                "ANSI/TIA-1057, Section 10.2.3.1"
        ::= { lldpMedRemMediaPolicyEntry 4 }

    lldpMedRemMediaPolicyVlanID  OBJECT-TYPE
        SYNTAX      Integer32 (0|1..4094|4095)
        MAX-ACCESS  read-only
        STATUS      current
        DESCRIPTION
                "An extension of the VLAN Identifier for the remote system
                 connected to this port, as defined in IEEE 802.1P-1998.

                 A value of 1 through 4094 is used to define a valid PVID.

                 A value of 0 shall be used if the device is using priority tagged
                 frames, meaning that only the 802.1p priority level is significant
                 and the default VID of the ingress port is being used instead.

                 A value of 4095 is reserved for implementation use."
        REFERENCE
                " ANSI/TIA-1057, Section 10.2.3.5"
        ::= { lldpMedRemMediaPolicyEntry 5 }

    lldpMedRemMediaPolicyPriority  OBJECT-TYPE
        SYNTAX      Integer32 (0..7)
        MAX-ACCESS  read-only
        STATUS      current
        DESCRIPTION
                "This object contains the value of the 802.1p priority
                which is associated with the remote system connected at
                given port."
        REFERENCE
                " ANSI/TIA-1057, Section 10.2.3.6"
        ::= { lldpMedRemMediaPolicyEntry 6 }

    lldpMedRemMediaPolicyDscp  OBJECT-TYPE
        SYNTAX      Dscp
        MAX-ACCESS  read-only
        STATUS      current
        DESCRIPTION
                "This object contains the value of the Differentiated Service
                Code Point (DSCP) as defined in IETF RFC 2474 and RFC 2475
                which is associated with remote system connected at the port."
        REFERENCE
                " ANSI/TIA-1057, Section 10.2.3.7"
        ::= { lldpMedRemMediaPolicyEntry 7 }

    lldpMedRemMediaPolicyUnknown  OBJECT-TYPE
        SYNTAX      TruthValue
        MAX-ACCESS  read-only
        STATUS      current
        DESCRIPTION
                "A value of 'true' indicates that the
                 network policy for the specified application type is
                 currently unknown.  In this case, the VLAN ID, the
                 layer 2 priority and the DSCP value fields are ignored.
                 A value of 'false' indicates that this network policy
                 is defined."
        REFERENCE
                " ANSI/TIA-1057, Section 10.2.3.2"
        ::= { lldpMedRemMediaPolicyEntry 8 }

    lldpMedRemMediaPolicyTagged  OBJECT-TYPE
        SYNTAX      TruthValue
        MAX-ACCESS  read-only
        STATUS      current
        DESCRIPTION
                "A value of 'true' indicates that the application is using a
                 tagged VLAN.
                 A value of 'false' indicates that for the specific application
                 the device either is using an untagged VLAN or does not
                 support port based VLAN operation.  In this case, both the
                 VLAN ID and the Layer 2 priority fields are ignored and
                 only the DSCP value has relevance "
        REFERENCE
                " ANSI/TIA-1057, Section 10.2.3.3"
        ::= { lldpMedRemMediaPolicyEntry 9 }

    lbdGlobal				OBJECT IDENTIFIER ::= { sysLBD 1}
	
-- LBD Group ------------------------------------------------------    
    lbdStatus OBJECT-TYPE 
			SYNTAX      INTEGER {
					enabled(1),
					disabled(2)
					}
			MAX-ACCESS  read-write 
			STATUS      current 
			DESCRIPTION 
					"Enable/Disable Loopback detection function.
					The Loopback Detection function is used to detect the loop created
					by a specific port while Spanning Tree Protocol (STP) is not 
					enabled in the network, especially when the down links are hubs 
					or unmanaged switchs.The Switch will automatically shutdown the 
					port and sends a log to the administrator."
			DEFVAL  { disabled }
			::= { lbdGlobal 1 }
        
    lbdInterval  OBJECT-TYPE
			SYNTAX      Integer32 (1..32767)
			MAX-ACCESS  read-write
			STATUS      current
			DESCRIPTION
					"Set a Loop detection Interval between 1 and 32767 seconds.
					The default is 2 seconds.
					This time interval to be used at counting time seconds to
					resend the CTP packet automatically."  
			DEFVAL  { 2 }
			::= { lbdGlobal 2 }
			
	lbdRecoverTime  OBJECT-TYPE
			SYNTAX      Integer32 (0 | 60..1000000)
			MAX-ACCESS  read-write
			STATUS      current
			DESCRIPTION
					"This time interval to be used at counting time seconds to
					recover the disabled port automatically. 
					The Loop Detection Recover Time can be set at 0 seconds, 
					or 60 to 1000000 seconds.
					Entering 0 will disable the Loop Detection Recover Time."  
			DEFVAL  { 60 }
			::= { lbdGlobal 3 }
                   
	-- LBD Port Control Table
        
	lbdCtrlTable OBJECT-TYPE 
			SYNTAX      SEQUENCE OF LbdCtrlEntry 
			MAX-ACCESS  not-accessible 
			STATUS      current 
			DESCRIPTION 
					"A table to control Loopback detection features either for 
					the entire switch or for each interface in the switch."
			::= { sysLBD 2 }
        
	lbdCtrlEntry OBJECT-TYPE 
			SYNTAX      LbdCtrlEntry 
			MAX-ACCESS  not-accessible 
			STATUS      current 
			DESCRIPTION 
					"An entry appears in this table for each interface 
					in the system."
			INDEX { lbdCtrlIndex }
			::= { lbdCtrlTable 1 }
           
	LbdCtrlEntry ::= 
			SEQUENCE { 
					lbdCtrlIndex
						Integer32, 
					lbdPortStatus 
						INTEGER, 
					lbdPortLoopStatus 
						INTEGER 
			}
        
	lbdCtrlIndex OBJECT-TYPE 
			SYNTAX      Integer32   (1..28) 
			MAX-ACCESS  read-only 
			STATUS      current
			DESCRIPTION 
					"The interface index of the port for which the configuration
					in this entry applies."
			::= { lbdCtrlEntry 1 }
		
	lbdPortStatus OBJECT-TYPE 
			SYNTAX      INTEGER {
					enabled(1),
					disabled(2)
					}
			MAX-ACCESS  read-write 
			STATUS      current 
			DESCRIPTION 
					"Provides control to per port enable or disable the loopback detection 
					function. Default is disabled."
			DEFVAL  { disabled }
			::= { lbdCtrlEntry 2 }
	
	lbdPortLoopStatus OBJECT-TYPE 
			SYNTAX      INTEGER {
					normal(1),
					loop(2)
					}
			MAX-ACCESS  read-only
			STATUS      current 
			DESCRIPTION 
					"The loop status for this port." 
			DEFVAL  { normal }

			::= { lbdCtrlEntry 3 }        
			
	lbdTraps                  OBJECT IDENTIFIER ::= { sysLBD 3 }
		
	lbdTrapsList		OBJECT IDENTIFIER ::= { lbdTraps 0 }
    lbdLoopOccur NOTIFICATION-TYPE
      STATUS             current
      DESCRIPTION
       "This is a trap that will send to snmp manager,and it will be generated when loop is occured."
 	::= {lbdTrapsList 1 }
	
	lbdLoopRecover NOTIFICATION-TYPE
      STATUS             current
      DESCRIPTION
       "This is a trap that will send to snmp manager,and it will be generated when port is recovering."
 	::= {lbdTrapsList 2 }

	
			
  
     sntpGeneralGroup       OBJECT IDENTIFIER ::= { sysSNTP 1 }
     sntpTzDSTGroup         OBJECT IDENTIFIER ::= { sysSNTP 2 }
          
-- Sntp General

	 sntpStatus OBJECT-TYPE
		SYNTAX     INTEGER {
            enable(1),
            disable(2)
          }
		MAX-ACCESS read-write 
		STATUS     current 
		DESCRIPTION 
			"This object is for enabling or disabling SNTP Client
		     feature in the system."
		DEFVAL { disable } 
		::= { sntpGeneralGroup 1 }
   
	 sntpPollInterval OBJECT-TYPE
		SYNTAX      Unsigned32 (1..60)
		UNITS       "minutes"
		MAX-ACCESS  read-write 
		STATUS      current 
		DESCRIPTION 
			"The number of minutes between successive SNTP request transmissions. "
		DEFVAL { 1 }
		::= { sntpGeneralGroup 2 }   
   
	 sntpDateTime OBJECT-TYPE
		SYNTAX      DisplayString 
		MAX-ACCESS  read-write 
		STATUS      current 
		DESCRIPTION 
			" The date is configured in the switch in the format, 
			 Hours:Minutes:Seconds Day Month Year
			 e.g 18:4:42 28 2 2022 
 	
			 01-12  Month - beginning from January to December
			 The railway time  00 to 24 hours can be configured and 
			 displayed. 
			 The Display of the date is in the format ,
			 WeekDay  Month  Day  Hours:Minutes:Seconds Year
			 e.g 04 09 21 18:11:30 2005 
 	
			 01-07  WeekDay - beginning from Sunday to Saturday
			 01-12  Month - beginning from January to December "
		::= { sntpGeneralGroup 3 }   

-- SntpServer Table
-- This table is for configuring the unicast server table

	 sntpServerTable OBJECT-TYPE
		SYNTAX      SEQUENCE OF SntpServerEntry
		MAX-ACCESS  not-accessible
		STATUS      current
		DESCRIPTION
            "The table contains configured SNTP/NTP servers in the system."
		::= { sntpGeneralGroup 4 }

	 sntpServerEntry  OBJECT-TYPE
		SYNTAX      SntpServerEntry
		MAX-ACCESS  not-accessible
		STATUS      current
		DESCRIPTION
            " Each entry in the table contains necessary information to
              send SNTP request to the servers."
        INDEX { sntpServerAddrType, sntpServerAddr }
		::= { sntpServerTable 1 }

	 SntpServerEntry ::= SEQUENCE {
		sntpServerAddrType         INTEGER,
		sntpServerAddr             InetAddress, 
		sntpServerInterfaceName    OCTET STRING,
		sntpServerType             INTEGER,		
		sntpServerRowStatus        RowStatus
	}

	 sntpServerAddrType OBJECT-TYPE
		SYNTAX		INTEGER {
						ipv4(1), 
   						ipv6(2),
						dns(3)
   					} 
		MAX-ACCESS  read-only 
		STATUS      current 
		DESCRIPTION 
			"The unicast IPv4/IPv6 server address in the Unicast Addressing mode.
			It supports hostname when the fsSntpUnicastServerAddrType is of DNS type" 
		DEFVAL { ipv4 } 
		::= { sntpServerEntry 1 }

	 sntpServerAddr OBJECT-TYPE
		SYNTAX      InetAddress
		MAX-ACCESS  read-only
		STATUS      current
		DESCRIPTION
			" The unicast IPv4/IPv6 server address in the Unicast Addressing mode "
		::= { sntpServerEntry 2}

	 sntpServerInterfaceName OBJECT-TYPE
	    SYNTAX      OCTET STRING (SIZE(1..32))
	    MAX-ACCESS  read-only
	    STATUS      current
	    DESCRIPTION
		   "Specifies the interface name from which the packet will be sent out when the sntpServerAddr is linklocal address."
	    ::= { sntpServerEntry 3 } 
			   
	 sntpServerType OBJECT-TYPE
		SYNTAX      INTEGER { primary  (1), secondary (2) }
		MAX-ACCESS  read-write
		STATUS      current
		DESCRIPTION
			"In Unicast addressing mode, we can have primary and secondary servers.
			 This flag is to distinguish between primary and secondary server.
			 SNTP client sends request to different servers until it receives
			 successful response. This flag tells the order in which to query the
			 servers."
--		DEFVAL { primary }
		::= { sntpServerEntry 4 }

	 sntpServerRowStatus OBJECT-TYPE
		SYNTAX      RowStatus
		MAX-ACCESS  read-write
		STATUS      current
		DESCRIPTION  
			" The activation of a row adds server entry. The destruction of a row
			 removes server entry"
		::= { sntpServerEntry 5 }   


-- SNTP Time Zone

	 sntpDSTStatus OBJECT-TYPE
		SYNTAX      INTEGER {
            enabled(1),
            disabled(2)
           }
		MAX-ACCESS  read-write 
		STATUS      current 
		DESCRIPTION 
			"This object is for enabling or disabling Time Zone Daylight Saving Time
             feature in the system."
	   
		DEFVAL { disabled } 
		::= { sntpTzDSTGroup 1 }

	 sntpTimeZone OBJECT-TYPE
		SYNTAX     INTEGER (0..65)
		MAX-ACCESS read-write
		STATUS     current
		DESCRIPTION
			"To set the system time zone with respect to UTC. ie plus indicates
			forward time zone ( ahead of UTC Time eg: +05:30) and minus indicates
			backward time zone (behind UTC time eg: -03:30). values you can set just
			as following:
			{
				0 : '(GMT-12:00) Eniwetok,Kwajalein'
				1 : '(GMT-11:00) Midway Island,Samoa'
				2 : '(GMT-10:00) Hawaii'
				3 : '(GMT-09:00) Alaska'
				4 : '(GMT-08:00) Pacific Time (US & Canada),Tijuana'        
				5 : '(GMT-07:00) Arizona'
				6 : '(GMT-07:00) Mountain Time (US & Canada)'
				7 : '(GMT-06:00) Central Time (US & Canada)'
				8 : '(GMT-06:00) Mexico City,Tegucigalpa'
				9 : '(GMT-06:00) Saskatchewan'
				10 : '(GMT-05:00) Bogota,Lima,Ouito'
				11 : '(GMT-05:00) Eastern Time (US & Canada)'
				12 : '(GMT-05:00) Indiana (East)'
				13 : '(GMT-04:00) Atlantic Time(Canada)'
				14 : '(GMT-04:00) Caracas,La Paz'
				15 : '(GMT-04:00) Sasntiago'
				16 : '(GMT-03:30) Newfoundland'
				17 : '(GMT-03:00) Brasilia'
				18 : '(GMT-03:00) Buenos Aires,Georgetown'
				19 : '(GMT-02:00) Mid-Atlantic'
				20 : '(GMT-01:00) Azores,Cape Verde Is.'
				21 : '(GMT)       Casablance, Monrovia'
				22 : '(GMT)       Greenwich Mean Time:Dublin,Edinburgh,Lisbon,London'
				23 : '(GMT+01:00) Amsterdam,Berlin,Bern,Rome,Stockholm,Vienna'
				24 : '(GMT+01:00) Belgrade,Bratislava,Budapest,Ljubljana,Prague'
				25 : '(GMT+01:00) Brussels,Copenhagen,Madrid,Paris,Vilnius'
				26 : '(GMT+01:00) Sarajevo,Skopje,Sofija,Warsaw,Zagreb'
				27 : '(GMT+02:00) Athens,Istanbul,Minsk'
				28 : '(GMT+02:00) Bucharest'
				29 : '(GMT+02:00) Cairo'
				30 : '(GMT+02:00) Harare,Pretoria'
				31 : '(GMT+02:00) Helsinki,riga,Tallinn'
				32 : '(GMT+02:00) Jerusalem'
				33 : '(GMT+03:00) Baghdad,kuwait,Riyadh'
				34 : '(GMT+03:00) Moscow,St.Petersburg,Volgograd'
				35 : '(GMT+03:00) Nairobi'
				36 : '(GMT+03:30) Tehran'
				37 : '(GMT+04:00) Abu Dhabi,Muscat'
				38 : '(GMT+04:00) Baku,Tbilisi'
				39 : '(GMT+04:30) Kabul'
				40 : '(GMT+05:00) Ekaterinburg'
				41 : '(GMT+05:00) Islamabad,Karachi,Tashkent'
				42 : '(GMT+05:30) Bombay,Calcutta,Madras,New Delhi'     
				43 : '(GMT+06:00) Astana,Almaty,Dhaka'
				44 : '(GMT+06:00) Colombo'
				45 : '(GMT+07:00) Bangkok,Hanoi,Jakarta'
				46 : '(GMT+08:00) Beijing,Chongqing, Hong Kong,Urumqi'
				47 : '(GMT+08:00) Perth'
				48 : '(GMT+08:00) Singapore'
				49 : '(GMT+08:00) Taipei'
				50 : '(GMT+09:00) Osaka,Sapporo,Tokyo'
				51 : '(GMT+09:00) Seoul'
				52 : '(GMT+09:00) Yakutsk'
				53 : '(GMT+09:30) Adelaide'
				54 : '(GMT+09:30) Darwin'
				55 : '(GMT+10:00) Brisbane'
				56 : '(GMT+10:00) Canberra,Melbourne,Sydney'
				57 : '(GMT+10:00) Guarn,Port Moresby'
				58 : '(GMT+10:00) Hobart'
				59 : '(GMT+10:00) Vladivostok'
				60 : '(GMT+11:00) Magadan,Solomon Is. ,New Calcdonia'
				61 : '(GMT+11:30) Norfolk Island'
				62 : '(GMT+12:00) Auckland,Wellington'
				63 : '(GMT+12:00) Fiji,Kamchatka,Marshall Is.' 
				65 : '(GMT+14:00) Kiribati (Line Islands)'
		}"
		DEFVAL { 4 }
		::= { sntpTzDSTGroup 2 }

	 sntpDSTStartTime OBJECT-TYPE
		SYNTAX     DisplayString (SIZE (12))
		MAX-ACCESS read-write
		STATUS     current
		DESCRIPTION
			" Daylight saving time (DST) is a system of setting clocks ahead so
			  that both sunrise and sunset occur at a later hour. The effect is
			  additional daylight in the evening. Many countries observe DST, 
			  although most have their own rules and regulations for when it begins
			  and ends. The dates of DST may change from year to year. The Valid 
			  format  [dayofmonth-month,HH:MM]. 
			  Example:- 01-Apr,17:30"   
		::= { sntpTzDSTGroup 5 }

 
	 sntpDSTEndTime OBJECT-TYPE
		SYNTAX     DisplayString (SIZE (12))
		MAX-ACCESS read-write
		STATUS     current
		DESCRIPTION
			" Daylight saving time (DST) is a system of setting clocks ahead so
			  that both sunrise and sunset occur at a later hour. The effect is
			  additional daylight in the evening. Many countries observe DST, 
			  although most have their own rules and regulations for when it begins
			  and ends. The dates of DST may change from year to year. The Valid 
			  format  [dayofmonth-month,HH:MM]. 
			  Example:- 01-Apr,17:30"   
		::= { sntpTzDSTGroup 6 }

	 sntpDSTFowardOffset  OBJECT-TYPE
	   SYNTAX       INTEGER  {
					halfHour (30),
					oneHour (60)
					}
	   MAX-ACCESS   read-write
	   STATUS       current
	   DESCRIPTION
		  "The adjusted time of Daylight Saving Time."

	   ::= { sntpTzDSTGroup 7 }		
  
  
     rmonGlobal         OBJECT IDENTIFIER ::= { sysRMON 1 }
     rmonStatistics     OBJECT IDENTIFIER ::= { sysRMON 2 }
	 rmonHistory        OBJECT IDENTIFIER ::= { sysRMON 3 }
     rmonAlarm          OBJECT IDENTIFIER ::= { sysRMON 4 }
	 rmonEvent          OBJECT IDENTIFIER ::= { sysRMON 5 }
	 
-- Rmon System

	 rmonEnableStatus OBJECT-TYPE
        SYNTAX  INTEGER { 
                     enabled(1),
                     disabled(2)
		} 
        MAX-ACCESS read-write
        STATUS current
        DESCRIPTION
			"This object defines the rmonenable flag for rmon" 
        ::=  { rmonGlobal  1 }  

-- The Ethernet Statistics Group

	 rmonEtherStatsTable OBJECT-TYPE
		SYNTAX     SEQUENCE OF RmonEtherStatsEntry
		MAX-ACCESS not-accessible
		STATUS     current
		DESCRIPTION
			"A list of Ethernet statistics entries."
		::= { rmonStatistics 1 }

	 rmonEtherStatsEntry OBJECT-TYPE
		SYNTAX     RmonEtherStatsEntry
		MAX-ACCESS not-accessible
		STATUS     current
		DESCRIPTION
			"A collection of statistics kept for a particular
			Ethernet interface.  As an example, an instance of the
			rmonEtherStatsPkts object might be named rmonEtherStatsPkts.1"
		INDEX { rmonEtherStatsIndex }
		::= { rmonEtherStatsTable 1 }

	 RmonEtherStatsEntry ::= SEQUENCE {
		rmonEtherStatsIndex                    Integer32,
		rmonEtherStatsDataSource               OBJECT IDENTIFIER,
		rmonEtherStatsDropEvents               Counter32,
		rmonEtherStatsOctets                   Counter32,
		rmonEtherStatsPkts                     Counter32,
        rmonEtherStatsBroadcastPkts            Counter32,
		rmonEtherStatsMulticastPkts            Counter32,
		rmonEtherStatsOwner                    DisplayString,
		rmonEtherStatsStatus                   RmonStatus
	 }

	 rmonEtherStatsIndex OBJECT-TYPE
		SYNTAX     Integer32 (1..65535)
		MAX-ACCESS read-only
		STATUS     current
		DESCRIPTION
			"The value of this object uniquely identifies this
			rmonEtherStats entry."
		::= { rmonEtherStatsEntry 1 }

	 rmonEtherStatsDataSource OBJECT-TYPE
		SYNTAX     OBJECT IDENTIFIER
		MAX-ACCESS read-create
		STATUS     current
		DESCRIPTION
			"This object identifies the source of the data that
			this etherStats entry is configured to analyze.  This
			source can be any ethernet interface on this device.
			In order to identify a particular interface, this object
			shall identify the instance of the ifIndex object,
			defined in RFC 2233 [17], for the desired interface.
			For example, if an entry were to receive data from
			interface #1, this object would be set to ifIndex.1.

			The statistics in this group reflect all packets
			on the local network segment attached to the identified
			interface.

			An agent may or may not be able to tell if fundamental
			changes to the media of the interface have occurred and
			necessitate an invalidation of this entry.  For example, a
			hot-pluggable ethernet card could be pulled out and replaced
			by a token-ring card.  In such a case, if the agent has such
			knowledge of the change, it is recommended that it
			invalidate this entry.

			This object may not be modified if the associated
			rmonEtherStatsStatus object is equal to valid(1)."
		::= { rmonEtherStatsEntry 2 }

	 rmonEtherStatsDropEvents OBJECT-TYPE
		SYNTAX     Counter32
		MAX-ACCESS read-only
		STATUS     current
		DESCRIPTION
			"The total number of events in which packets
			were dropped by the probe due to lack of resources.
			Note that this number is not necessarily the number of
			packets dropped; it is just the number of times this
			condition has been detected."
		::= { rmonEtherStatsEntry 3 }

	 rmonEtherStatsOctets OBJECT-TYPE
		SYNTAX     Counter32
		UNITS      "Octets"
		MAX-ACCESS read-only
		STATUS     current
		DESCRIPTION
			"The total number of octets of data (including
			those in bad packets) received on the
			network (excluding framing bits but including
			FCS octets).

			This object can be used as a reasonable estimate of
			10-Megabit ethernet utilization.  If greater precision is
			desired, the etherStatsPkts and etherStatsOctets objects
			should be sampled before and after a common interval.  The
			differences in the sampled values are Pkts and Octets,
			respectively, and the number of seconds in the interval is
			Interval.  These values are used to calculate the Utilization
			as follows:

                          Pkts * (9.6 + 6.4) + (Octets * .8)
			Utilization = -------------------------------------
                                  Interval * 10,000

			The result of this equation is the value Utilization which
			is the percent utilization of the ethernet segment on a
			scale of 0 to 100 percent."
		::= { rmonEtherStatsEntry 4 }

	 rmonEtherStatsPkts OBJECT-TYPE
		SYNTAX     Counter32
		UNITS      "Packets"
		MAX-ACCESS read-only
		STATUS     current
		DESCRIPTION
			"The total number of packets (including bad packets,
			broadcast packets, and multicast packets) received."
		::= { rmonEtherStatsEntry 5 }

     rmonEtherStatsBroadcastPkts OBJECT-TYPE
		SYNTAX     Counter32
		UNITS      "Packets"
		MAX-ACCESS read-only
		STATUS     current
		DESCRIPTION
			"The total number of good packets received that were
			directed to the broadcast address.  Note that this
			does not include multicast packets."
		::= { rmonEtherStatsEntry 6 }

	 rmonEtherStatsMulticastPkts OBJECT-TYPE
		SYNTAX     Counter32
		UNITS      "Packets"
		MAX-ACCESS read-only
		STATUS     current
		DESCRIPTION
			"The total number of good packets received that were
			directed to a multicast address.  Note that this number
			does not include packets directed to the broadcast
			address."
		::= { rmonEtherStatsEntry 7 }

	 rmonEtherStatsOwner OBJECT-TYPE
		SYNTAX     DisplayString (SIZE (0..32))
		MAX-ACCESS read-create
		STATUS     current
		DESCRIPTION
			"The entity that configured this entry and is therefore
			using the resources assigned to it."
		::= { rmonEtherStatsEntry 20 }

	 rmonEtherStatsStatus OBJECT-TYPE
		SYNTAX     RmonStatus
		MAX-ACCESS read-create
		STATUS     current
		DESCRIPTION
			"The status of this etherStats entry."
		::= { rmonEtherStatsEntry 21 }  
		
-- The History control Group
	 rmonHistoryControlTable OBJECT-TYPE
		SYNTAX     SEQUENCE OF RmonHistoryControlEntry
		MAX-ACCESS not-accessible
		STATUS     current
		DESCRIPTION
			"A list of history control entries."
		::= { rmonHistory 1 }

	 rmonHistoryControlEntry OBJECT-TYPE
		SYNTAX     RmonHistoryControlEntry
		MAX-ACCESS not-accessible
		STATUS     current
		DESCRIPTION
			"A list of parameters that set up a periodic sampling of
			statistics.  As an example, an instance of the
			rmonHistoryControlInterval object might be named
			rmonHistoryControlInterval.2"
		INDEX { rmonHistoryControlIndex }
		::= { rmonHistoryControlTable 1 }

	 RmonHistoryControlEntry ::= SEQUENCE {
		rmonHistoryControlIndex             Integer32,
		rmonHistoryControlDataSource        OBJECT IDENTIFIER,
		rmonHistoryControlBucketsRequested  Integer32,
		rmonHistoryControlBucketsGranted    Integer32,
		rmonHistoryControlInterval          Integer32,
		rmonHistoryControlOwner             DisplayString,
		rmonHistoryControlStatus            RmonStatus
	}

	 rmonHistoryControlIndex OBJECT-TYPE
		SYNTAX     Integer32 (1..65535)
		MAX-ACCESS read-only
		STATUS     current
		DESCRIPTION
			"An index that uniquely identifies an entry in the
			rmonHistoryControl table.  Each such entry defines a
			set of samples at a particular interval for an
			interface on the device."
		::= { rmonHistoryControlEntry 1 }

	 rmonHistoryControlDataSource OBJECT-TYPE
		SYNTAX     OBJECT IDENTIFIER
		MAX-ACCESS read-create
		STATUS     current
		DESCRIPTION
			"This object identifies the source of the data for
			which historical data was collected and
			placed in a media-specific table on behalf of this
			rmonHistoryControlEntry.  This source can be any
			interface on this device.  In order to identify

			a particular interface, this object shall identify
			the instance of the ifIndex object, defined
			in  RFC 2233 [17], for the desired interface.
			For example, if an entry were to receive data from
			interface #1, this object would be set to ifIndex.1.

			The statistics in this group reflect all packets
			on the local network segment attached to the identified
			interface.

			An agent may or may not be able to tell if fundamental
			changes to the media of the interface have occurred and
			necessitate an invalidation of this entry.  For example, a
			hot-pluggable ethernet card could be pulled out and replaced
			by a token-ring card.  In such a case, if the agent has such
			knowledge of the change, it is recommended that it
			invalidate this entry.

			This object may not be modified if the associated
			rmonHistoryControlStatus object is equal to valid(1)."
		::= { rmonHistoryControlEntry 2 }

	 rmonHistoryControlBucketsRequested OBJECT-TYPE
		SYNTAX     Integer32 (1..50)
		MAX-ACCESS read-create
		STATUS     current
		DESCRIPTION
			"The requested number of discrete time intervals
			over which data is to be saved in the part of the
			media-specific table associated with this
			rmonHistoryControlEntry.

			When this object is created or modified, the probe
			should set rmonHistoryControlBucketsGranted as closely to
			this object as is possible for the particular probe
			implementation and available resources."
		DEFVAL { 50 }
		::= { rmonHistoryControlEntry 3 }

	 rmonHistoryControlBucketsGranted OBJECT-TYPE
		SYNTAX     Integer32 (1..50)
		MAX-ACCESS read-only
		STATUS     current
		DESCRIPTION
			"The number of discrete sampling intervals
			over which data shall be saved in the part of
			the media-specific table associated with this
			cusRmonHistoryControlEntry.

			When the associated rmonHistoryControlBucketsRequested
			object is created or modified, the probe
			should set this object as closely to the requested
			value as is possible for the particular
			probe implementation and available resources.  The
			probe must not lower this value except as a result
			of a modification to the associated
			rmonHistoryControlBucketsRequested object.

			There will be times when the actual number of
			buckets associated with this entry is less than
			the value of this object.  In this case, at the
			end of each sampling interval, a new bucket will
			be added to the media-specific table.

			When the number of buckets reaches the value of
			this object and a new bucket is to be added to the
			media-specific table, the oldest bucket associated
			with this rmonHistoryControlEntry shall be deleted by
			the agent so that the new bucket can be added.

			When the value of this object changes to a value less
			than the current value, entries are deleted
			from the media-specific table associated with this
			rmonHistoryControlEntry.  Enough of the oldest of these
			entries shall be deleted by the agent so that their
			number remains less than or equal to the new value of
			this object.

			When the value of this object changes to a value greater
			than the current value, the number of associated media-
			specific entries may be allowed to grow."
		::= { rmonHistoryControlEntry 4 }

	 rmonHistoryControlInterval OBJECT-TYPE
		SYNTAX     Integer32 (1..3600)
		UNITS      "Seconds"
		MAX-ACCESS read-create
		STATUS     current
		DESCRIPTION
			"The interval in seconds over which the data is
			sampled for each bucket in the part of the
			media-specific table associated with this
			rmonHistoryControlEntry.  This interval can
			be set to any number of seconds between 1 and
			3600 (1 hour).

			Because the counters in a bucket may overflow at their

			maximum value with no indication, a prudent manager will
			take into account the possibility of overflow in any of
			the associated counters.  It is important to consider the
			minimum time in which any counter could overflow on a
			particular media type and set the rmonHistoryControlInterval
			object to a value less than this interval.  This is
			typically most important for the 'octets' counter in any
			media-specific table.  For example, on an Ethernet
			network, the rmonEtherHistoryOctets counter could overflow
			in about one hour at the Ethernet's maximum
			utilization.

			This object may not be modified if the associated
			rmonHistoryControlStatus object is equal to valid(1)."
		DEFVAL { 1800 }
		::= { rmonHistoryControlEntry 5 }

	 rmonHistoryControlOwner OBJECT-TYPE
		SYNTAX     DisplayString (SIZE (0..32))
		MAX-ACCESS read-create
		STATUS     current
		DESCRIPTION
			"The entity that configured this entry and is therefore
			using the resources assigned to it."
		::= { rmonHistoryControlEntry 6 }

	 rmonHistoryControlStatus OBJECT-TYPE
		SYNTAX     RmonStatus
		MAX-ACCESS read-create
		STATUS     current
		DESCRIPTION
			"The status of this historyControl entry.

			Each instance of the media-specific table associated
			with this rmonHistoryControlEntry will be deleted by the agent
			if this rmonHistoryControlEntry is not equal to valid(1)."
		::= { rmonHistoryControlEntry 7 }
		
-- The alarm control Group

	 rmonAlarmTable OBJECT-TYPE
		SYNTAX     SEQUENCE OF RmonAlarmEntry
		MAX-ACCESS not-accessible
		STATUS     current
		DESCRIPTION
			"A list of alarm entries."
		::= { rmonAlarm 1 }

	 rmonAlarmEntry OBJECT-TYPE
		SYNTAX     RmonAlarmEntry
		MAX-ACCESS not-accessible
		STATUS     current
		DESCRIPTION
			"A list of parameters that set up a periodic checking
			for alarm conditions."
		INDEX { rmonAlarmIndex }
		::= { rmonAlarmTable 1 }

	 RmonAlarmEntry ::= SEQUENCE {
		rmonAlarmIndex                    Integer32,
		rmonAlarmInterval                 Integer32,
		rmonAlarmVariable                 OBJECT IDENTIFIER,
		rmonAlarmSampleType               INTEGER,
		rmonAlarmRisingThreshold          Integer32,
		rmonAlarmFallingThreshold         Integer32,
		rmonAlarmRisingEventIndex         Integer32,
		rmonAlarmFallingEventIndex        Integer32,
		rmonAlarmOwner                    DisplayString,
		rmonAlarmStatus                   RmonStatus
	}

	 rmonAlarmIndex OBJECT-TYPE
		SYNTAX     Integer32 (1..65535)
		MAX-ACCESS read-only
		STATUS     current
		DESCRIPTION
			"An index that uniquely identifies an entry in the
			alarm table.  Each such entry defines a
			diagnostic sample at a particular interval
			for an object on the device."
		::= { rmonAlarmEntry 1 }

	 rmonAlarmInterval OBJECT-TYPE
		SYNTAX     Integer32 (1..2147483647)
		UNITS      "Seconds"
		MAX-ACCESS read-create
		STATUS     current
		DESCRIPTION
			"The interval in seconds over which the data is
			sampled and compared with the rising and falling
			thresholds.  When setting this variable, care
			should be taken in the case of deltaValue
			sampling - the interval should be set short enough
			that the sampled variable is very unlikely to
			increase or decrease by more than 2^31 - 1 during
			a single sampling interval.

			This object may not be modified if the associated
			rmonAlarmStatus object is equal to valid(1)."
		::= { rmonAlarmEntry 2 }

	 rmonAlarmVariable OBJECT-TYPE
		SYNTAX     OBJECT IDENTIFIER
		MAX-ACCESS read-create
		STATUS     current
		DESCRIPTION
			"The object identifier of the particular variable to be
			sampled.  Only variables that resolve to an ASN.1 primitive
			type of INTEGER (INTEGER, Integer32, Counter32, Counter64,
			Gauge, or TimeTicks) may be sampled.

			Because SNMP access control is articulated entirely
			in terms of the contents of MIB views, no access
			control mechanism exists that can restrict the value of
			this object to identify only those objects that exist
			in a particular MIB view.  Because there is thus no
			acceptable means of restricting the read access that
			could be obtained through the alarm mechanism, the
			probe must only grant write access to this object in

			those views that have read access to all objects on
			the probe.

			During a set operation, if the supplied variable name is
			not available in the selected MIB view, a badValue error
			must be returned.  If at any time the variable name of
			an established rmonAlarmEntry is no longer available in the
			selected MIB view, the probe must change the status of
			this rmonAlarmEntry to invalid(4).

			This object may not be modified if the associated
			rmonAlarmStatus object is equal to valid(1)."
		::= { rmonAlarmEntry 3 }

	 rmonAlarmSampleType OBJECT-TYPE
		SYNTAX     INTEGER {
                  absoluteValue(1),
                  deltaValue(2)
                }
		MAX-ACCESS read-create
		STATUS     current
		DESCRIPTION
			"The method of sampling the selected variable and
			calculating the value to be compared against the
			thresholds.  If the value of this object is
			absoluteValue(1), the value of the selected variable
			will be compared directly with the thresholds at the
			end of the sampling interval.  If the value of this
			object is deltaValue(2), the value of the selected
			variable at the last sample will be subtracted from
			the current value, and the difference compared with
			the thresholds.

			This object may not be modified if the associated
			rmonAlarmStatus object is equal to valid(1)."
		::= { rmonAlarmEntry 4 }

	 rmonAlarmRisingThreshold OBJECT-TYPE
		SYNTAX     Integer32
		MAX-ACCESS read-create
		STATUS     current
		DESCRIPTION
			"A threshold for the sampled statistic.  When the current
			sampled value is greater than or equal to this threshold,
			and the value at the last sampling interval was less than
			this threshold, a single event will be generated.
			A single event will also be generated if the first
			sample after this entry becomes valid is greater than or
			equal to this threshold and the associated
			alarmStartupAlarm is equal to risingAlarm(1) or
			risingOrFallingAlarm(3).

			After a rising event is generated, another such event

			will not be generated until the sampled value
			falls below this threshold and reaches the
			rmonAlarmFallingThreshold.

			This object may not be modified if the associated
			rmonAlarmStatus object is equal to valid(1)."
		::= { rmonAlarmEntry 5 }

	 rmonAlarmFallingThreshold OBJECT-TYPE
		SYNTAX     Integer32
		MAX-ACCESS read-create
		STATUS     current
		DESCRIPTION
			"A threshold for the sampled statistic.  When the current
			sampled value is less than or equal to this threshold,
			and the value at the last sampling interval was greater than
			this threshold, a single event will be generated.
			A single event will also be generated if the first
			sample after this entry becomes valid is less than or
			equal to this threshold and the associated
			alarmStartupAlarm is equal to fallingAlarm(2) or
			risingOrFallingAlarm(3).

			After a falling event is generated, another such event
			will not be generated until the sampled value
			rises above this threshold and reaches the
			rmonAlarmRisingThreshold.

			This object may not be modified if the associated
			rmonalarmStatus object is equal to valid(1)."
		::= { rmonAlarmEntry 6 }

	 rmonAlarmRisingEventIndex OBJECT-TYPE
		SYNTAX     Integer32 (0..65535)
		MAX-ACCESS read-create
		STATUS     current
		DESCRIPTION
			"The index of the rmonEventEntry that is
			used when a rising threshold is crossed.  The
			rmonEventEntry identified by a particular value of
			this index is the same as identified by the same value
			of the rmonEventIndex object.  If there is no
			corresponding entry in the rmonEventTable, then
			no association exists.  In particular, if this value
			is zero, no associated event will be generated, as
			zero is not a valid event index.

			This object may not be modified if the associated

			rmonAlarmStatus object is equal to valid(1)."
		::= { rmonAlarmEntry 7 }

	 rmonAlarmFallingEventIndex OBJECT-TYPE
		SYNTAX     Integer32 (0..65535)
		MAX-ACCESS read-create
		STATUS     current
		DESCRIPTION
			"The index of the rmonEventEntry that is
			used when a falling threshold is crossed.  The
			rmonEventEntry identified by a particular value of
			this index is the same as identified by the same value
			of the rmonEventIndex object.  If there is no
			corresponding entry in the rmonEventTable, then
			no association exists.  In particular, if this value
			is zero, no associated event will be generated, as
			zero is not a valid event index.

			This object may not be modified if the associated
			rmonAlarmStatus object is equal to valid(1)."
		::= { rmonAlarmEntry 8 }

	 rmonAlarmOwner OBJECT-TYPE
		SYNTAX     DisplayString (SIZE (0..32))
		MAX-ACCESS read-create
		STATUS     current
		DESCRIPTION
			"The entity that configured this entry and is therefore
			using the resources assigned to it."
		::= { rmonAlarmEntry 9 }

	 rmonAlarmStatus OBJECT-TYPE
		SYNTAX     RmonStatus
		MAX-ACCESS read-create
		STATUS     current
		DESCRIPTION
			"The status of this alarm entry."
		::= { rmonAlarmEntry 10 }

-- The event control Group	

	 rmonEventTable OBJECT-TYPE
		SYNTAX     SEQUENCE OF RmonEventEntry
		MAX-ACCESS not-accessible
		STATUS     current
		DESCRIPTION
			"A list of events to be generated."
		::= { rmonEvent 1 }

	 rmonEventEntry OBJECT-TYPE
		SYNTAX     RmonEventEntry
		MAX-ACCESS not-accessible
		STATUS     current
		DESCRIPTION
			"A set of parameters that describe an event to be generated
			when certain conditions are met.  As an example, an instance
			of the rmonEventLastTimeSent object might be named
			rmonEventLastTimeSent.6"
		INDEX { rmonEventIndex }
		::= { rmonEventTable 1 }

	 RmonEventEntry ::= SEQUENCE {
		rmonEventIndex          Integer32,
		rmonEventDescription    DisplayString,
		rmonEventType           INTEGER,
		rmonEventCommunity      DisplayString,
		rmonEventLastTimeSent   TimeTicks,
		rmonEventOwner          DisplayString,
		rmonEventStatus         RmonStatus
	}

	 rmonEventIndex OBJECT-TYPE
		SYNTAX     Integer32 (1..65535)
		MAX-ACCESS read-only
		STATUS     current
		DESCRIPTION
			"An index that uniquely identifies an entry in the
			event table.  Each such entry defines one event that
			is to be generated when the appropriate conditions
			occur."
		::= { rmonEventEntry 1 }

	 rmonEventDescription OBJECT-TYPE
		SYNTAX     DisplayString (SIZE (0..32))
		MAX-ACCESS read-create
		STATUS     current
		DESCRIPTION
			"A comment describing this event entry."
		::= { rmonEventEntry 2 }

	 rmonEventType OBJECT-TYPE
		SYNTAX     INTEGER {
                  none(1),
                  log(2),
                  snmptrap(3),    -- send an SNMP trap
                  logandtrap(4)
                }
		MAX-ACCESS read-create
		STATUS     current
		DESCRIPTION
			"The type of notification that the probe will make
			about this event.  In the case of log, an entry is
			made in the log table for each event.  In the case of
			snmp-trap, an SNMP trap is sent to one or more
			management stations."
		::= { rmonEventEntry 3 }

	 rmonEventCommunity OBJECT-TYPE
		SYNTAX     DisplayString (SIZE (0..127))
		MAX-ACCESS read-create
		STATUS     current
		DESCRIPTION
			"If an SNMP trap is to be sent, it will be sent to
			the SNMP community specified by this octet string."
		::= { rmonEventEntry 4 }

	 rmonEventLastTimeSent OBJECT-TYPE
		SYNTAX     TimeTicks
		MAX-ACCESS read-only
		STATUS     current
		DESCRIPTION
			"The value of sysUpTime at the time this event
			entry last generated an event.  If this entry has
			not generated any events, this value will be
			zero."
		::= { rmonEventEntry 5 }

	 rmonEventOwner OBJECT-TYPE
		SYNTAX     DisplayString (SIZE (0..32))
		MAX-ACCESS read-create
		STATUS     current
		DESCRIPTION
			"The entity that configured this entry and is therefore
			using the resources assigned to it.

			If this object contains a string starting with 'monitor'
			and has associated entries in the log table, all connected
			management stations should retrieve those log entries,
			as they may have significance to all management stations
			connected to this device"
		::= { rmonEventEntry 6 }

	 rmonEventStatus OBJECT-TYPE
		SYNTAX     RmonStatus
		MAX-ACCESS read-create
		STATUS     current
		DESCRIPTION
			"The status of this event entry.

			If this object is not equal to valid(1), all associated
			log entries shall be deleted by the agent."
		::= { rmonEventEntry 7 } 
		
-- snmp group	
	snmpGlobal                OBJECT IDENTIFIER ::= { sysSNMP 1 }
	snmpUser                  OBJECT IDENTIFIER ::= { sysSNMP 2 }
    snmpGroup                 OBJECT IDENTIFIER ::= { sysSNMP 3 }
    snmpViewTree              OBJECT IDENTIFIER ::= { sysSNMP 4 }
    snmpCommunity             OBJECT IDENTIFIER ::= { sysSNMP 5 }
    snmpTrapManager           OBJECT IDENTIFIER ::= { sysSNMP 6 }
-- snmpGlobal group	
      snmpGlobalState OBJECT-TYPE 
           SYNTAX      INTEGER {
                          enabled(1),
                          disabled(2)
                       }
           MAX-ACCESS  read-write 
           STATUS      current 
           DESCRIPTION 
               "This object is used to enable/disable the SNMP agent."        
           ::= { snmpGlobal 1 }
		   
      snmpTrapEnable OBJECT-TYPE 
           SYNTAX      INTEGER {
                          enabled(1),
                          disabled(2)
                       }
           MAX-ACCESS  read-write 
           STATUS      current 
           DESCRIPTION 
               "This object is used to enable/disable the SNMP trap."        
           ::= { snmpGlobal 2 }    

      
      snmpEngineID OBJECT-TYPE
              SYNTAX  SnmpEngineID 
              MAX-ACCESS read-write
              STATUS current
		      DESCRIPTION 
		         "An SNMP engine's administratively-unique identifier.

                 In a simple agent, this value is always that agent's
                 own snmpEngineID value.

                 The value can also take the value of the snmpEngineID
                 of a remote SNMP engine with which this user can
                 communicate."

         ::=  { snmpGlobal  3 }
      
--      cusSnmpTrap                    OBJECT IDENTIFIER ::= { cusSnmp 9 } 
--    cusSnmpStatistic               OBJECT IDENTIFIER ::= { cusSnmp 10 }
      
      -- ----------------------------------------------------------------
      -- The snmpUser group
      -- ----------------------------------------------------------------

      snmpUserTable OBJECT-TYPE
           SYNTAX SEQUENCE OF SnmpUserEntry
           MAX-ACCESS not-accessible
           STATUS     current
           DESCRIPTION
              ""
           ::= { snmpUser 1 }
        
      snmpUserEntry OBJECT-TYPE
           SYNTAX      SnmpUserEntry
           MAX-ACCESS  not-accessible
           STATUS      current
           DESCRIPTION
              ""
           INDEX { snmpUserName, snmpUserVersion}
           ::= { snmpUserTable 1 }
      
      SnmpUserEntry ::= SEQUENCE {
                snmpUserName                      SnmpAdminString,
                snmpUserVersion                   INTEGER,
                snmpUserGroupName                 SnmpAdminString,
                snmpUserAuthProtocol              INTEGER,
                snmpUserAuthProtocolPassword      SnmpAdminString,
                snmpUserPrivProtocol              INTEGER, 
                snmpUserPrivProtocolPassword      SnmpAdminString,             
                snmpUserStatus                    RowStatus
            }

		snmpUserName       OBJECT-TYPE
				SYNTAX       SnmpAdminString (SIZE(1..32))
				MAX-ACCESS   read-only
				STATUS       current
				DESCRIPTION "A human readable string representing the name of
							 the user.
			
							 This is the (User-based Security) Model dependent
							 security ID.
							"
		  ::= { snmpUserEntry 1 }
    
        snmpUserVersion  OBJECT-TYPE
            SYNTAX    INTEGER {
                      v1            (1),
                      v2c	        (2),
                      v3            (3)
                   }
            MAX-ACCESS   read-only
            STATUS       current
            DESCRIPTION "A human readable string representing the name of
                         the user.
        
                         This is the (User-based Security) Model dependent
                         security ID.
                        "
            ::= { snmpUserEntry 2 }           

                  
        snmpUserGroupName      OBJECT-TYPE
            SYNTAX       SnmpAdminString (SIZE(1..32))
            MAX-ACCESS   read-create
            STATUS       current
            DESCRIPTION "The name of the group to which this entry (e.g., the
                         combination of securityModel and securityName)
                         belongs.
        
                         This groupName is used as index into the
                         vacmAccessTable to select an access control policy.
                         However, a value in this table does not imply that an
                         instance with the value exists in table vacmAccesTable.
                        "
            ::= { snmpUserEntry 3 }                             

        snmpUserAuthProtocol OBJECT-TYPE
            SYNTAX    INTEGER {
                      none          (1),
                      md5	        (2),
                      sha           (3)
                   }
            MAX-ACCESS   read-create
            STATUS       current
            DESCRIPTION "An indication of whether messages sent on behalf of
                 this user to/from the SNMP engine identified by
                 usmUserEngineID, can be authenticated, and if so,
                 the type of authentication protocol which is used.

                 An instance of this object is created concurrently
                 with the creation of any other object instance for
                 the same user (i.e., as part of the processing of
                 the set operation which creates the first object
                 instance in the same conceptual row).

                 If an initial set operation (i.e. at row creation time)
                 tries to set a value for an unknown or unsupported
                 protocol, then a 'wrongValue' error must be returned.

                 The value will be overwritten/set when a set operation
                 is performed on the corresponding instance of
                 UserCloneFrom.

                 Once instantiated, the value of such an instance of
                 this object can only be changed via a set operation to
                 the value of the NoAuthProtocol.

                 If a set operation tries to change the value of an


                 existing instance of this object to any value other
                 than NoAuthProtocol, then an 'inconsistentValue'
                 error must be returned.

                 If a set operation tries to set the value to the
                 NoAuthProtocol while the UserPrivProtocol value
                 in the same row is not equal to NoPrivProtocol,
                 then an 'inconsistentValue' error must be returned.
                 That means that an SNMP command generator application
                 must first ensure that the UserPrivProtocol is set
                 to the NoPrivProtocol value before it can set
                 the UserAuthProtocol value to NoAuthProtocol.
                "
            ::= { snmpUserEntry 4 }
       
        snmpUserAuthProtocolPassword OBJECT-TYPE
			SYNTAX       SnmpAdminString (SIZE(1..32))
				MAX-ACCESS   read-create
				STATUS       current
				DESCRIPTION  ""
				::= { snmpUserEntry 5 }    
            
        
        snmpUserPrivProtocol OBJECT-TYPE
            SYNTAX    INTEGER {
                      none          (1),
                      des	        (2)
                   }
            MAX-ACCESS   read-create
            STATUS       current
            DESCRIPTION "An indication of whether messages sent on behalf of
                 this user to/from the SNMP engine identified by
                 usmUserEngineID, can be protected from disclosure,
                 and if so, the type of privacy protocol which is used.

                 An instance of this object is created concurrently
                 with the creation of any other object instance for
                 the same user (i.e., as part of the processing of
                 the set operation which creates the first object
                 instance in the same conceptual row).

                 If an initial set operation (i.e. at row creation time)
                 tries to set a value for an unknown or unsupported
                 protocol, then a 'wrongValue' error must be returned.

                 The value will be overwritten/set when a set operation
                 is performed on the corresponding instance of
                 usmUserCloneFrom.

                 Once instantiated, the value of such an instance of
                 this object can only be changed via a set operation to
                 the value of the NoPrivProtocol.

                 If a set operation tries to change the value of an
                 existing instance of this object to any value other
                 than NoPrivProtocol, then an 'inconsistentValue'
                 error must be returned.

                 Note that if any privacy protocol is used, then you
                 must also use an authentication protocol. In other
                 words, if usmUserPrivProtocol is set to anything else
                 than NoPrivProtocol, then the corresponding instance
                 of usmUserAuthProtocol cannot have a value of

                 usmNoAuthProtocol. If it does, then an
                 'inconsistentValue' error must be returned.
                "
            ::= { snmpUserEntry 6 }

        snmpUserPrivProtocolPassword OBJECT-TYPE
			SYNTAX       SnmpAdminString (SIZE(1..32))
				MAX-ACCESS   read-create
				STATUS       current
				DESCRIPTION  ""
				::= { snmpUserEntry 7 }   


        snmpUserStatus  OBJECT-TYPE
            SYNTAX       RowStatus
            MAX-ACCESS   read-create
            STATUS       current
            DESCRIPTION "The status of this conceptual row.

                 Until instances of all corresponding columns are
                 appropriately configured, the value of the
                 corresponding instance of the usmUserStatus column
                 is 'notReady'.

                 In particular, a newly created row for a user who
                 employs authentication, cannot be made active until the
                 corresponding usmUserCloneFrom and usmUserAuthKeyChange
                 have been set.

                 Further, a newly created row for a user who also
                 employs privacy, cannot be made active until the
                 usmUserPrivKeyChange has been set.

                 The RowStatus TC [RFC2579] requires that this
                 DESCRIPTION clause states under which circumstances
                 other objects in this row can be modified:

                 The value of this object has no effect on whether
                 other objects in this conceptual row can be modified,
                 except for usmUserOwnAuthKeyChange and
                 usmUserOwnPrivKeyChange. For these 2 objects, the
                 value of usmUserStatus MUST be active.
                "
				::= { snmpUserEntry 8 }


      -- ----------------------------------------------------------------
      -- The snmpGroup group
      -- ----------------------------------------------------------------
        snmpGroupTable OBJECT-TYPE
           SYNTAX SEQUENCE OF SnmpGroupEntry
           MAX-ACCESS not-accessible
           STATUS     current
           DESCRIPTION
              ""
           ::= { snmpGroup 1 }
        
        snmpGroupEntry OBJECT-TYPE
           SYNTAX      SnmpGroupEntry
           MAX-ACCESS  not-accessible
           STATUS      current
           DESCRIPTION
              ""
           INDEX { snmpGroupName ,snmpGroupSecurityModel ,snmpGroupSecurityLevel}   
           ::= { snmpGroupTable 1 }
              
        SnmpGroupEntry ::= SEQUENCE {
                snmpGroupName              SnmpAdminString,
                snmpGroupSecurityModel     INTEGER,
                snmpGroupSecurityLevel     SnmpSecurityLevel,
                snmpGroupReadViewName      SnmpAdminString,
                snmpGroupWriteViewName     SnmpAdminString,
                snmpGroupNotifyViewName    SnmpAdminString,
                snmpGroupStatus            RowStatus
            }
        
        snmpGroupName  OBJECT-TYPE
            SYNTAX       SnmpAdminString (SIZE(1..32))
            MAX-ACCESS   read-only
            STATUS       current
            DESCRIPTION "The name of the group to which this entry (e.g., the
                         combination of securityModel and securityName)
                         belongs.
        
                         This groupName is used as index into the
                         vacmAccessTable to select an access control policy.
                         However, a value in this table does not imply that an
                         instance with the value exists in table vacmAccesTable.
                        "
            ::= { snmpGroupEntry 1 }    
        
        snmpGroupSecurityModel OBJECT-TYPE
            SYNTAX    INTEGER {
                      v1            (1),
                      v2c	        (2),
                      v3            (3)
                   }
            MAX-ACCESS   read-only
            STATUS       current
            DESCRIPTION "In order to gain the access rights allowed by this
                         conceptual row, this securityModel must be in use.
                        "
            ::= { snmpGroupEntry 2 }
        
        snmpGroupSecurityLevel OBJECT-TYPE
            SYNTAX       SnmpSecurityLevel
            MAX-ACCESS   read-only
            STATUS       current
            DESCRIPTION "The minimum level of security required in order to
                         gain the access rights allowed by this conceptual
                         row.  A securityLevel of noAuthNoPriv is less than
                         authNoPriv which in turn is less than authPriv.
        
                         If multiple entries are equally indexed except for
                         this vacmAccessSecurityLevel index, then the entry
                         which has the highest value for
                         vacmAccessSecurityLevel is selected.
                        "
            ::= { snmpGroupEntry 3 }
        
        snmpGroupReadViewName OBJECT-TYPE
            SYNTAX       SnmpAdminString (SIZE(0..32))
            MAX-ACCESS   read-create
            STATUS       current
            DESCRIPTION "The value of an instance of this object identifies
                         the MIB view of the SNMP context to which this
                         conceptual row authorizes read access.
        
                         The identified MIB view is that one for which the
                         vacmViewTreeFamilyViewName has the same value as the
                         instance of this object; if the value is the empty
                         string or if there is no active MIB view having this
                         value of vacmViewTreeFamilyViewName, then no access
                         is granted.
                        "
        --    DEFVAL      { ''H }   -- -- the empty string --
            ::= { snmpGroupEntry 4 }
        
        snmpGroupWriteViewName OBJECT-TYPE
            SYNTAX       SnmpAdminString (SIZE(0..32))
            MAX-ACCESS   read-create
            STATUS       current
            DESCRIPTION "The value of an instance of this object identifies
                         the MIB view of the SNMP context to which this
                         conceptual row authorizes write access.
        
                         The identified MIB view is that one for which the
                         vacmViewTreeFamilyViewName has the same value as the
                         instance of this object; if the value is the empty
                         string or if there is no active MIB view having this
                         value of vacmViewTreeFamilyViewName, then no access
                         is granted.
                        "
        --    DEFVAL      { ''H }   -- -- the empty string --
        
            ::= { snmpGroupEntry 5 }
        
        snmpGroupNotifyViewName OBJECT-TYPE
            SYNTAX       SnmpAdminString (SIZE(0..32))
            MAX-ACCESS   read-create
            STATUS       current
            DESCRIPTION "The value of an instance of this object identifies
                         the MIB view of the SNMP context to which this
                         conceptual row authorizes access for notifications.
        
                         The identified MIB view is that one for which the
                         vacmViewTreeFamilyViewName has the same value as the
                         instance of this object; if the value is the empty
                         string or if there is no active MIB view having this
                         value of vacmViewTreeFamilyViewName, then no access
                         is granted.
                        "
        --    DEFVAL      { ''H }   -- -- the empty string --
            ::= { snmpGroupEntry 6 }
        
        snmpGroupStatus     OBJECT-TYPE
            SYNTAX       RowStatus
            MAX-ACCESS   read-create
            STATUS       current
            DESCRIPTION "The status of this conceptual row.
        
                         The  RowStatus TC [RFC2579] requires that this
                         DESCRIPTION clause states under which circumstances
                         other objects in this row can be modified:
        
                         The value of this object has no effect on whether
                         other objects in this conceptual row can be modified.
                        "
            ::= { snmpGroupEntry 7 }


      -- ----------------------------------------------------------------
      -- The snmpViewTree group
      -- ----------------------------------------------------------------
        snmpViewTreeTable OBJECT-TYPE
           SYNTAX SEQUENCE OF SnmpViewTreeEntry
           MAX-ACCESS not-accessible
           STATUS     current
           DESCRIPTION
              ""
           ::= { snmpViewTree 1 }
        
        snmpViewTreeEntry OBJECT-TYPE
           SYNTAX      SnmpViewTreeEntry
           MAX-ACCESS  not-accessible
           STATUS      current
           DESCRIPTION
              ""
           INDEX { snmpViewTreeName ,snmpViewTreeSubtree }      
           ::= { snmpViewTreeTable 1 }
              
        SnmpViewTreeEntry ::= SEQUENCE
            {
                snmpViewTreeName         SnmpAdminString,
                snmpViewTreeSubtree      OBJECT IDENTIFIER,
                snmpViewTreeMask         OCTET STRING,
                snmpViewTreeType         INTEGER,
                snmpViewTreeStatus       RowStatus
            }
        
        snmpViewTreeName OBJECT-TYPE
            SYNTAX       SnmpAdminString (SIZE(1..32))
            MAX-ACCESS   read-only
            STATUS       current
            DESCRIPTION "The human readable name for a family of view subtrees.
                        "
        
            ::= { snmpViewTreeEntry 1 }
        
        snmpViewTreeSubtree OBJECT-TYPE
            SYNTAX       OBJECT IDENTIFIER
            MAX-ACCESS   read-only
            STATUS       current
            DESCRIPTION "The MIB subtree which when combined with the
                         corresponding instance of vacmViewTreeFamilyMask
                         defines a family of view subtrees.
                        "
            ::= { snmpViewTreeEntry 2 }
        
        snmpViewTreeMask OBJECT-TYPE
            SYNTAX       OCTET STRING (SIZE (0..16))
            MAX-ACCESS   read-create
            STATUS       current
            DESCRIPTION "The bit mask which, in combination with the
                         corresponding instance of vacmViewTreeFamilySubtree,
                         defines a family of view subtrees.
        
                         Each bit of this bit mask corresponds to a
                         sub-identifier of vacmViewTreeFamilySubtree, with the
                         most significant bit of the i-th octet of this octet
                         string value (extended if necessary, see below)
                         corresponding to the (8*i - 7)-th sub-identifier, and
                         the least significant bit of the i-th octet of this
                         octet string corresponding to the (8*i)-th
                         sub-identifier, where i is in the range 1 through 16.
        
                         Each bit of this bit mask specifies whether or not
                         the corresponding sub-identifiers must match when
                         determining if an OBJECT IDENTIFIER is in this
                         family of view subtrees; a '1' indicates that an
                         exact match must occur; a '0' indicates 'wild card',
                         i.e., any sub-identifier value matches.
        
                         Thus, the OBJECT IDENTIFIER X of an object instance
                         is contained in a family of view subtrees if, for
                         each sub-identifier of the value of
                         vacmViewTreeFamilySubtree, either:
        
                           the i-th bit of vacmViewTreeFamilyMask is 0, or
        
                           the i-th sub-identifier of X is equal to the i-th
                           sub-identifier of the value of
                           vacmViewTreeFamilySubtree.
        
                         If the value of this bit mask is M bits long and
        
                         there are more than M sub-identifiers in the
                         corresponding instance of vacmViewTreeFamilySubtree,
                         then the bit mask is extended with 1's to be the
                         required length.
        
                         Note that when the value of this object is the
                         zero-length string, this extension rule results in
                         a mask of all-1's being used (i.e., no 'wild card'),
                         and the family of view subtrees is the one view
                         subtree uniquely identified by the corresponding
                         instance of vacmViewTreeFamilySubtree.
        
                         Note that masks of length greater than zero length
                         do not need to be supported.  In this case this
                         object is made read-only.
                        "
        --    DEFVAL      { ''H }
            ::= { snmpViewTreeEntry 3 }
        
        snmpViewTreeType OBJECT-TYPE
            SYNTAX       INTEGER  { included(1), excluded(2) }
            MAX-ACCESS   read-create
            STATUS       current
            DESCRIPTION "Indicates whether the corresponding instances of
                         vacmViewTreeFamilySubtree and vacmViewTreeFamilyMask
                         define a family of view subtrees which is included in
                         or excluded from the MIB view.
                        "
        --    DEFVAL      { included }
            ::= { snmpViewTreeEntry 4 }
        
        snmpViewTreeStatus OBJECT-TYPE
            SYNTAX       RowStatus
            MAX-ACCESS   read-create
            STATUS       current
            DESCRIPTION "The status of this conceptual row.
        
                         The  RowStatus TC [RFC2579] requires that this
                         DESCRIPTION clause states under which circumstances
                         other objects in this row can be modified:
        
                         The value of this object has no effect on whether
                         other objects in this conceptual row can be modified.
                        "
            ::= { snmpViewTreeEntry 5 }
    

      -- ----------------------------------------------------------------
      -- The snmpCommunity group
      -- ----------------------------------------------------------------

        snmpCommunityTable OBJECT-TYPE
           SYNTAX SEQUENCE OF SnmpCommunityEntry
           MAX-ACCESS not-accessible
           STATUS     current
           DESCRIPTION
              ""
           ::= { snmpCommunity 1 }
        
        snmpCommunityEntry OBJECT-TYPE
           SYNTAX      SnmpCommunityEntry
           MAX-ACCESS  not-accessible
           STATUS      current
           DESCRIPTION
              ""
           INDEX { snmpCommunityName }
           ::= { snmpCommunityTable 1 }
              
        SnmpCommunityEntry ::= SEQUENCE
            {
                snmpCommunityName                SnmpAdminString,
                snmpCommunityPolicy              SnmpAdminString,
                snmpCommunityStatus              RowStatus
            }    
        
        snmpCommunityName OBJECT-TYPE
            SYNTAX      SnmpAdminString
            MAX-ACCESS  read-only
            STATUS      current
            DESCRIPTION
                "The community string for which a row in this table
				represents a configuration.  There is no SIZE constraint
				specified for this object because RFC 1157 does not
				impose any explicit limitation on the length of community
				strings (their size is constrained indirectly by the
				SNMP message size)"
            ::= { snmpCommunityEntry 1 }

        snmpCommunityPolicy OBJECT-TYPE
            SYNTAX       SnmpAdminString (SIZE(1..32))
            MAX-ACCESS   read-create
            STATUS       current
            DESCRIPTION
                "A human readable string representing the corresponding
                 value of snmpCommunityName in a Security Model
                 independent format."
            ::= { snmpCommunityEntry 2 }
			
        snmpCommunityStatus OBJECT-TYPE
            SYNTAX       RowStatus
            MAX-ACCESS   read-create
            STATUS       current
            DESCRIPTION
                "The status of this conceptual row in the
                 snmpCommunityTable.
        
                 An entry in this table is not qualified for activation
                 until instances of all corresponding columns have been
                 initialized, either through default values, or through
                 Set operations.  The snmpCommunityName and
                 snmpCommunitySecurityName objects must be explicitly set.
        
                 There is no restriction on setting columns in this table
                 when the value of snmpCommunityStatus is active(1)."
            ::= { snmpCommunityEntry 3 }


      -- ----------------------------------------------------------------
      -- The snmpTrapManager group
      -- ----------------------------------------------------------------

        snmpTrapManagerTable OBJECT-TYPE
           SYNTAX SEQUENCE OF SnmpTrapManagerEntry
           MAX-ACCESS not-accessible
           STATUS     current
           DESCRIPTION
              ""
           ::= { snmpTrapManager 1 }

        snmpTrapManagerEntry OBJECT-TYPE
           SYNTAX      SnmpTrapManagerEntry
           MAX-ACCESS  not-accessible
           STATUS      current
           DESCRIPTION
              ""
           INDEX { snmpTrapManagerAddrType, snmpTrapManagerAddress }
           ::= { snmpTrapManagerTable 1 }
              
        SnmpTrapManagerEntry ::= SEQUENCE
            {  
				snmpTrapManagerAddrType         INTEGER,			
                snmpTrapManagerAddress           InetAddress,
				snmpTrapManagerInterfaceName 	 DisplayString,
                snmpTrapManagerSecurityName      SnmpAdminString,
                snmpTrapManagerSecurityLevel     INTEGER,				
                snmpTrapManagerStatus            RowStatus       
            }    
        
		snmpTrapManagerAddrType OBJECT-TYPE
			SYNTAX		INTEGER {
							ipv4(1), 
							ipv6(2) 
						} 
			MAX-ACCESS  read-only 
			STATUS      current 
			DESCRIPTION 
				"The IP address type ipv4 or ipv6." 
			DEFVAL { ipv4 } 
			::= { snmpTrapManagerEntry 1 }
		
        snmpTrapManagerAddress OBJECT-TYPE
               SYNTAX      InetAddress
               MAX-ACCESS  read-only
               STATUS      current
               DESCRIPTION
                   "This object contains a transport address. "
               ::= { snmpTrapManagerEntry 2 }
               
		snmpTrapManagerInterfaceName OBJECT-TYPE
               SYNTAX      DisplayString (SIZE(1..32))
               MAX-ACCESS  read-only
               STATUS      current
               DESCRIPTION
                   "Specifies the interface name from which the trap will be sent out when the snmpTrapManagerAddress is linklocal address."
               ::= { snmpTrapManagerEntry 3 }
			   
        snmpTrapManagerSecurityName OBJECT-TYPE
               SYNTAX      SnmpAdminString (SIZE(1..32))
               MAX-ACCESS  read-create
               STATUS      current
               DESCRIPTION
                   "The name of security to be used when gnerating SNMP messages using this entry."
               ::= { snmpTrapManagerEntry 4 } 
               
        
        snmpTrapManagerSecurityLevel OBJECT-TYPE
               SYNTAX    INTEGER {
                      v1                (1),
                      v2c	            (2),
                      v3NoAuthNoPriv    (3),
                      v3AuthNoPriv      (4),
                      v3AuthPriv        (5)
                   }
               MAX-ACCESS  read-create
               STATUS      current
               DESCRIPTION
                   "The Level of security to be used when generating
                    SNMP messages using this entry."
               ::= { snmpTrapManagerEntry 5 }
        
        snmpTrapManagerStatus OBJECT-TYPE
               SYNTAX       RowStatus
               MAX-ACCESS   read-create
               STATUS       current
               DESCRIPTION
                ""
               ::= { snmpTrapManagerEntry 6 }       


	qosTrafficCtrl OBJECT IDENTIFIER ::= { sysQoS 2 }
	qosDiffServ	OBJECT IDENTIFIER ::= { sysQoS 3 }
	qosDefaultUserPri OBJECT IDENTIFIER ::= { sysQoS 4 }
	--qosIP6TrafficClass OBJECT IDENTIFIER ::= { sysQoS 5 }
	
--- COSQ schedule global config
	
	cosQueuingMechanism OBJECT-TYPE
	    SYNTAX      INTEGER {
	                strictPriority(1),
	                weightedRoundRobin(2)
	    }
	    MAX-ACCESS  read-write
	    STATUS      current
	    DESCRIPTION
	        "Sets the packet scheduling algorithm for all ports
	
	        The default is strictPriority(1)."
	
	    ::= { sysQoS 1 }

-- -------------------------------------------------------------
-- Traffic Class Table
-- -------------------------------------------------------------
	cosGlobalStatus       OBJECT-TYPE 
		SYNTAX INTEGER  {
							enabled(1),
							disabled(2)
						}
		MAX-ACCESS    read-write 
		STATUS        current
		DESCRIPTION 
			   "This object indicates cos function is enabled or disabled 
				for device.
				When you enable cos control function, it
				will allowed you to configure the queue for traffic class." 
		DEFVAL  {disabled}			
		::= { qosTrafficCtrl 1 } 
		
	qosTrafficClassTable OBJECT-TYPE
	    SYNTAX      SEQUENCE OF QosTrafficClassEntry
	    MAX-ACCESS  not-accessible
	    STATUS      current
	    DESCRIPTION
	        "A table mapping evaluated User Priority to Traffic
	        Class, for forwarding by the bridge.  Traffic class is a
	        number in the range (0..(dot1dPortNumTrafficClasses-1))."
	    REFERENCE
	        "ISO/IEC 15802-3 Table 7-2"
	    ::= { qosTrafficCtrl 2 }
	
	qosTrafficClassEntry OBJECT-TYPE
	    SYNTAX      QosTrafficClassEntry
	    MAX-ACCESS  not-accessible
	    STATUS      current
	    DESCRIPTION
	        "User Priority to Traffic Class mapping."
	    INDEX   {qosTrafficClassPriority }
	    ::= { qosTrafficClassTable 1 }
	
	QosTrafficClassEntry ::=
	    SEQUENCE {
	        qosTrafficClassPriority
	            INTEGER,
	        qosTrafficClass
	            INTEGER
	    }
	
	qosTrafficClassPriority OBJECT-TYPE
	    SYNTAX      INTEGER (0..7)
	    MAX-ACCESS  read-only
	    STATUS      current
	    DESCRIPTION
	        "The Priority value determined for the received frame.
	        This value is equivalent to the priority indicated in
	        the tagged frame received, or one of the evaluated
	        priorities, determined according to the media-type.
	
	        For untagged frames received from Ethernet media, this
	        value is equal to the dot1dPortDefaultUserPriority value
	        for the ingress port.
	
	        For untagged frames received from non-Ethernet media,
	        this value is equal to the dot1dRegenUserPriority value
	        for the ingress port and media-specific user priority."
	    ::= { qosTrafficClassEntry 1 }
	
	qosTrafficClass OBJECT-TYPE
	    SYNTAX      INTEGER (0..7)
	    MAX-ACCESS  read-write
	    STATUS      current
	    DESCRIPTION
	        "The Traffic Class the received frame is mapped to."
	    ::= {qosTrafficClassEntry 2 }

-- 	qosDiffServTypeGroup

 	qosDiffServType   OBJECT IDENTIFIER ::= { qosDiffServ 2 }
	
	qosDiffServStatus OBJECT-TYPE
	   SYNTAX     INTEGER {
	               enabled(1),
	               disabled(2)
	              }
	   MAX-ACCESS read-write
	   STATUS     current
	   DESCRIPTION
	      "Enable / Disable DiffServ function"
	   ::= { qosDiffServ 1 }
	
	qosDiffServType01 OBJECT-TYPE
	   SYNTAX     Integer32  (0..7)
	   MAX-ACCESS read-write
	   STATUS     current
	   DESCRIPTION
	      "DiffServ Type 01 : IP ToS value = 0"
	   ::= { qosDiffServType 1 }
	
	qosDiffServType02 OBJECT-TYPE
	   SYNTAX     Integer32  (0..7)
	   MAX-ACCESS read-write
	   STATUS     current
	   DESCRIPTION
	      "DiffServ Type 02 : IP ToS value = 4"
	   ::= { qosDiffServType 2 }
	
	qosDiffServType03 OBJECT-TYPE
	   SYNTAX     Integer32  (0..7)
	   MAX-ACCESS read-write
	   STATUS     current
	   DESCRIPTION
	      "DiffServ Type 03 : IP ToS value = 8"
	   ::= { qosDiffServType 3 }
	
	qosDiffServType04 OBJECT-TYPE
	   SYNTAX     Integer32  (0..7)
	   MAX-ACCESS read-write
	   STATUS     current
	   DESCRIPTION
	      "DiffServ Type 04 : IP ToS value = 12"
	   ::= { qosDiffServType 4 }
	
	qosDiffServType05 OBJECT-TYPE
	   SYNTAX     Integer32  (0..7)
	   MAX-ACCESS read-write
	   STATUS     current
	   DESCRIPTION
	      "DiffServ Type 05 : IP ToS value = 16"
	   ::= { qosDiffServType 5 }
	
	qosDiffServType06 OBJECT-TYPE
	   SYNTAX     Integer32  (0..7)
	   MAX-ACCESS read-write
	   STATUS     current
	   DESCRIPTION
	      "DiffServ Type 06 : IP ToS value = 20"
	   ::= { qosDiffServType 6 }
	
	qosDiffServType07 OBJECT-TYPE
	   SYNTAX     Integer32  (0..7)
	   MAX-ACCESS read-write
	   STATUS     current
	   DESCRIPTION
	      "DiffServ Type 07 : IP ToS value = 24"
	   ::= { qosDiffServType 7 }
	
	qosDiffServType08 OBJECT-TYPE
	   SYNTAX     Integer32  (0..7)
	   MAX-ACCESS read-write
	   STATUS     current
	   DESCRIPTION
	      "DiffServ Type 08 : IP ToS value = 28"
	   ::= { qosDiffServType 8 }
	
	qosDiffServType09 OBJECT-TYPE
	   SYNTAX     Integer32  (0..7)
	   MAX-ACCESS read-write
	   STATUS     current
	   DESCRIPTION
	      "DiffServ Type 09 : IP ToS value = 32"
	   ::= { qosDiffServType 9 }
	
	qosDiffServType10 OBJECT-TYPE
	   SYNTAX     Integer32  (0..7)
	   MAX-ACCESS read-write
	   STATUS     current
	   DESCRIPTION
	      "DiffServ Type 10 : IP ToS value = 36"
	   ::= { qosDiffServType 10 }
	
	qosDiffServType11 OBJECT-TYPE
	   SYNTAX     Integer32  (0..7)
	   MAX-ACCESS read-write
	   STATUS     current
	   DESCRIPTION
	      "DiffServ Type 11 : IP ToS value = 40"
	   ::= { qosDiffServType 11 }
	
	qosDiffServType12 OBJECT-TYPE
	   SYNTAX     Integer32  (0..7)
	   MAX-ACCESS read-write
	   STATUS     current
	   DESCRIPTION
	      "DiffServ Type 12 : IP ToS value = 44"
	   ::= { qosDiffServType 12 }
	
	qosDiffServType13 OBJECT-TYPE
	   SYNTAX     Integer32  (0..7)
	   MAX-ACCESS read-write
	   STATUS     current
	   DESCRIPTION
	      "DiffServ Type 13 : IP ToS value = 48"
	   ::= { qosDiffServType 13 }
	
	qosDiffServType14 OBJECT-TYPE
	   SYNTAX     Integer32  (0..7)
	   MAX-ACCESS read-write
	   STATUS     current
	   DESCRIPTION
	      "DiffServ Type 14 : IP ToS value = 52"
	   ::= { qosDiffServType 14 }
	
	qosDiffServType15 OBJECT-TYPE
	   SYNTAX     Integer32  (0..7)
	   MAX-ACCESS read-write
	   STATUS     current
	   DESCRIPTION
	      "DiffServ Type 15 : IP ToS value = 56"
	   ::= { qosDiffServType 15 }
	
	qosDiffServType16 OBJECT-TYPE
	   SYNTAX     Integer32  (0..7)
	   MAX-ACCESS read-write
	   STATUS     current
	   DESCRIPTION
	      "DiffServ Type 16 : IP ToS value = 60"
	   ::= { qosDiffServType 16 }
	
	qosDiffServType17 OBJECT-TYPE
	   SYNTAX     Integer32  (0..7)
	   MAX-ACCESS read-write
	   STATUS     current
	   DESCRIPTION
	      "DiffServ Type 17 : IP ToS value = 64"
	   ::= { qosDiffServType 17 }
	
	qosDiffServType18 OBJECT-TYPE
	   SYNTAX     Integer32  (0..7)
	   MAX-ACCESS read-write
	   STATUS     current
	   DESCRIPTION
	      "DiffServ Type 18 : IP ToS value = 68"
	   ::= { qosDiffServType 18 }
	
	qosDiffServType19 OBJECT-TYPE
	   SYNTAX     Integer32  (0..7)
	   MAX-ACCESS read-write
	   STATUS     current
	   DESCRIPTION
	      "DiffServ Type 19 : IP ToS value = 72"
	   ::= { qosDiffServType 19 }
	
	qosDiffServType20 OBJECT-TYPE
	   SYNTAX     Integer32  (0..7)
	   MAX-ACCESS read-write
	   STATUS     current
	   DESCRIPTION
	      "DiffServ Type 20 : IP ToS value = 76"
	   ::= { qosDiffServType 20 }
	
	qosDiffServType21 OBJECT-TYPE
	   SYNTAX     Integer32  (0..7)
	   MAX-ACCESS read-write
	   STATUS     current
	   DESCRIPTION
	      "DiffServ Type 21 : IP ToS value = 80"
	   ::= { qosDiffServType 21 }
	
	qosDiffServType22 OBJECT-TYPE
	   SYNTAX     Integer32  (0..7)
	   MAX-ACCESS read-write
	   STATUS     current
	   DESCRIPTION
	      "DiffServ Type 22 : IP ToS value = 84"
	   ::= { qosDiffServType 22 }
	
	qosDiffServType23 OBJECT-TYPE
	   SYNTAX     Integer32  (0..7)
	   MAX-ACCESS read-write
	   STATUS     current
	   DESCRIPTION
	      "DiffServ Type 23 : IP ToS value = 88"
	   ::= { qosDiffServType 23 }
	
	qosDiffServType24 OBJECT-TYPE
	   SYNTAX     Integer32  (0..7)
	   MAX-ACCESS read-write
	   STATUS     current
	   DESCRIPTION
	      "DiffServ Type 24 : IP ToS value = 92"
	   ::= { qosDiffServType 24 }
	
	qosDiffServType25 OBJECT-TYPE
	   SYNTAX     Integer32  (0..7)
	   MAX-ACCESS read-write
	   STATUS     current
	   DESCRIPTION
	      "DiffServ Type 25 : IP ToS value = 96"
	   ::= { qosDiffServType 25 }
	
	qosDiffServType26 OBJECT-TYPE
	   SYNTAX     Integer32  (0..7)
	   MAX-ACCESS read-write
	   STATUS     current
	   DESCRIPTION
	      "DiffServ Type 26 : IP ToS value = 100"
	   ::= { qosDiffServType 26 }
	
	qosDiffServType27 OBJECT-TYPE
	   SYNTAX     Integer32  (0..7)
	   MAX-ACCESS read-write
	   STATUS     current
	   DESCRIPTION
	      "DiffServ Type 27 : IP ToS value = 104"
	   ::= { qosDiffServType 27 }
	
	qosDiffServType28 OBJECT-TYPE
	   SYNTAX     Integer32  (0..7)
	   MAX-ACCESS read-write
	   STATUS     current
	   DESCRIPTION
	      "DiffServ Type 28 : IP ToS value = 108"
	   ::= { qosDiffServType 28 }
	
	qosDiffServType29 OBJECT-TYPE
	   SYNTAX     Integer32  (0..7)
	   MAX-ACCESS read-write
	   STATUS     current
	   DESCRIPTION
	      "DiffServ Type 29 : IP ToS value = 112"
	   ::= { qosDiffServType 29 }
	
	qosDiffServType30 OBJECT-TYPE
	   SYNTAX     Integer32  (0..7)
	   MAX-ACCESS read-write
	   STATUS     current
	   DESCRIPTION
	      "DiffServ Type 30 : IP ToS value = 116"
	   ::= { qosDiffServType 30 }
	
	qosDiffServType31 OBJECT-TYPE
	   SYNTAX     Integer32  (0..7)
	   MAX-ACCESS read-write
	   STATUS     current
	   DESCRIPTION
	      "DiffServ Type 31 : IP ToS value = 120"
	   ::= { qosDiffServType 31 }
	
	qosDiffServType32 OBJECT-TYPE
	   SYNTAX     Integer32  (0..7)
	   MAX-ACCESS read-write
	   STATUS     current
	   DESCRIPTION
	      "DiffServ Type 32 : IP ToS value = 124"
	   ::= { qosDiffServType 32 }
	
	qosDiffServType33 OBJECT-TYPE
	   SYNTAX     Integer32  (0..7)
	   MAX-ACCESS read-write
	   STATUS     current
	   DESCRIPTION
	      "DiffServ Type 33 : IP ToS value = 128"
	   ::= { qosDiffServType 33 }
	
	qosDiffServType34 OBJECT-TYPE
	   SYNTAX     Integer32  (0..7)
	   MAX-ACCESS read-write
	   STATUS     current
	   DESCRIPTION
	      "DiffServ Type 34 : IP ToS value = 132"
	   ::= { qosDiffServType 34 }
	
	qosDiffServType35 OBJECT-TYPE
	   SYNTAX     Integer32  (0..7)
	   MAX-ACCESS read-write
	   STATUS     current
	   DESCRIPTION
	      "DiffServ Type 35 : IP ToS value = 136"
	   ::= { qosDiffServType 35 }
	
	qosDiffServType36 OBJECT-TYPE
	   SYNTAX     Integer32  (0..7)
	   MAX-ACCESS read-write
	   STATUS     current
	   DESCRIPTION
	      "DiffServ Type 36 : IP ToS value = 140"
	   ::= { qosDiffServType 36 }
	
	qosDiffServType37 OBJECT-TYPE
	   SYNTAX     Integer32  (0..7)
	   MAX-ACCESS read-write
	   STATUS     current
	   DESCRIPTION
	      "DiffServ Type 37 : IP ToS value = 144"
	   ::= { qosDiffServType 37 }
	
	qosDiffServType38 OBJECT-TYPE
	   SYNTAX     Integer32  (0..7)
	   MAX-ACCESS read-write
	   STATUS     current
	   DESCRIPTION
	      "DiffServ Type 38 : IP ToS value = 148"
	   ::= { qosDiffServType 38 }
	
	qosDiffServType39 OBJECT-TYPE
	   SYNTAX     Integer32  (0..7)
	   MAX-ACCESS read-write
	   STATUS     current
	   DESCRIPTION
	      "DiffServ Type 39 : IP ToS value = 152"
	   ::= { qosDiffServType 39 }
	
	qosDiffServType40 OBJECT-TYPE
	   SYNTAX     Integer32  (0..7)
	   MAX-ACCESS read-write
	   STATUS     current
	   DESCRIPTION
	      "DiffServ Type 40 : IP ToS value = 156"
	   ::= { qosDiffServType 40 }
	
	qosDiffServType41 OBJECT-TYPE
	   SYNTAX     Integer32  (0..7)
	   MAX-ACCESS read-write
	   STATUS     current
	   DESCRIPTION
	      "DiffServ Type 41 : IP ToS value = 160"
	   ::= { qosDiffServType 41 }
	
	qosDiffServType42 OBJECT-TYPE
	   SYNTAX     Integer32  (0..7)
	   MAX-ACCESS read-write
	   STATUS     current
	   DESCRIPTION
	      "DiffServ Type 42 : IP ToS value = 164"
	   ::= { qosDiffServType 42 }
	
	qosDiffServType43 OBJECT-TYPE
	   SYNTAX     Integer32  (0..7)
	   MAX-ACCESS read-write
	   STATUS     current
	   DESCRIPTION
	      "DiffServ Type 43 : IP ToS value = 168"
	   ::= { qosDiffServType 43 }
	
	qosDiffServType44 OBJECT-TYPE
	   SYNTAX     Integer32  (0..7)
	   MAX-ACCESS read-write
	   STATUS     current
	   DESCRIPTION
	      "DiffServ Type 44 : IP ToS value = 172"
	   ::= { qosDiffServType 44 }
	
	qosDiffServType45 OBJECT-TYPE
	   SYNTAX     Integer32  (0..7)
	   MAX-ACCESS read-write
	   STATUS     current
	   DESCRIPTION
	      "DiffServ Type 45 : IP ToS value = 176"
	   ::= { qosDiffServType 45 }
	
	qosDiffServType46 OBJECT-TYPE
	   SYNTAX     Integer32  (0..7)
	   MAX-ACCESS read-write
	   STATUS     current
	   DESCRIPTION
	      "DiffServ Type 46 : IP ToS value = 180"
	   ::= { qosDiffServType 46 }
	
	qosDiffServType47 OBJECT-TYPE
	   SYNTAX     Integer32  (0..7)
	   MAX-ACCESS read-write
	   STATUS     current
	   DESCRIPTION
	      "DiffServ Type 47 : IP ToS value = 184"
	   ::= { qosDiffServType 47 }
	
	qosDiffServType48 OBJECT-TYPE
	   SYNTAX     Integer32  (0..7)
	   MAX-ACCESS read-write
	   STATUS     current
	   DESCRIPTION
	      "DiffServ Type 48 : IP ToS value = 188"
	   ::= { qosDiffServType 48 }
	
	qosDiffServType49 OBJECT-TYPE
	   SYNTAX     Integer32  (0..7)
	   MAX-ACCESS read-write
	   STATUS     current
	   DESCRIPTION
	      "DiffServ Type 49 : IP ToS value = 192"
	   ::= { qosDiffServType 49 }
	
	qosDiffServType50 OBJECT-TYPE
	   SYNTAX     Integer32  (0..7)
	   MAX-ACCESS read-write
	   STATUS     current
	   DESCRIPTION
	      "DiffServ Type 50 : IP ToS value = 196"
	   ::= { qosDiffServType 50 }
	
	qosDiffServType51 OBJECT-TYPE
	   SYNTAX     Integer32  (0..7)
	   MAX-ACCESS read-write
	   STATUS     current
	   DESCRIPTION
	      "DiffServ Type 51 : IP ToS value = 200"
	   ::= { qosDiffServType 51 }
	
	qosDiffServType52 OBJECT-TYPE
	   SYNTAX     Integer32  (0..7)
	   MAX-ACCESS read-write
	   STATUS     current
	   DESCRIPTION
	      "DiffServ Type 52 : IP ToS value = 204"
	   ::= { qosDiffServType 52 }
	
	qosDiffServType53 OBJECT-TYPE
	   SYNTAX     Integer32  (0..7)
	   MAX-ACCESS read-write
	   STATUS     current
	   DESCRIPTION
	      "DiffServ Type 53 : IP ToS value = 208"
	   ::= { qosDiffServType 53 }
	
	qosDiffServType54 OBJECT-TYPE
	   SYNTAX     Integer32  (0..7)
	   MAX-ACCESS read-write
	   STATUS     current
	   DESCRIPTION
	      "DiffServ Type 54 : IP ToS value = 212"
	   ::= { qosDiffServType 54 }
	
	qosDiffServType55 OBJECT-TYPE
	   SYNTAX     Integer32  (0..7)
	   MAX-ACCESS read-write
	   STATUS     current
	   DESCRIPTION
	      "DiffServ Type 55 : IP ToS value = 216"
	   ::= { qosDiffServType 55 }
	
	qosDiffServType56 OBJECT-TYPE
	   SYNTAX     Integer32  (0..7)
	   MAX-ACCESS read-write
	   STATUS     current
	   DESCRIPTION
	      "DiffServ Type 56 : IP ToS value = 220"
	   ::= { qosDiffServType 56 }
	
	qosDiffServType57 OBJECT-TYPE
	   SYNTAX     Integer32  (0..7)
	   MAX-ACCESS read-write
	   STATUS     current
	   DESCRIPTION
	      "DiffServ Type 57 : IP ToS value = 224"
	   ::= { qosDiffServType 57 }
	
	qosDiffServType58 OBJECT-TYPE
	   SYNTAX     Integer32  (0..7)
	   MAX-ACCESS read-write
	   STATUS     current
	   DESCRIPTION
	      "DiffServ Type 58 : IP ToS value = 228"
	   ::= { qosDiffServType 58 }
	
	qosDiffServType59 OBJECT-TYPE
	   SYNTAX     Integer32  (0..7)
	   MAX-ACCESS read-write
	   STATUS     current
	   DESCRIPTION
	      "DiffServ Type 59 : IP ToS value = 232"
	   ::= { qosDiffServType 59 }
	
	qosDiffServType60 OBJECT-TYPE
	   SYNTAX     Integer32  (0..7)
	   MAX-ACCESS read-write
	   STATUS     current
	   DESCRIPTION
	      "DiffServ Type 60 : IP ToS value = 236"
	   ::= { qosDiffServType 60 }
	
	qosDiffServType61 OBJECT-TYPE
	   SYNTAX     Integer32  (0..7)
	   MAX-ACCESS read-write
	   STATUS     current
	   DESCRIPTION
	      "DiffServ Type 61 : IP ToS value = 240"
	   ::= { qosDiffServType 61 }
	
	qosDiffServType62 OBJECT-TYPE
	   SYNTAX     Integer32  (0..7)
	   MAX-ACCESS read-write
	   STATUS     current
	   DESCRIPTION
	      "DiffServ Type 62 : IP ToS value = 244"
	   ::= { qosDiffServType 62 }
	
	qosDiffServType63 OBJECT-TYPE
	   SYNTAX     Integer32  (0..7)
	   MAX-ACCESS read-write
	   STATUS     current
	   DESCRIPTION
	      "DiffServ Type 63 : IP ToS value = 248"
	   ::= { qosDiffServType 63 }
	
	qosDiffServType64 OBJECT-TYPE
	   SYNTAX     Integer32  (0..7)
	   MAX-ACCESS read-write
	   STATUS     current
	   DESCRIPTION
	      "DiffServ Type 64 : IP ToS value = 252"
	   ::= { qosDiffServType 64 }
		
-- Port User Default Priority Table

	qosDefaultUserPriTable OBJECT-TYPE
	   SYNTAX      SEQUENCE OF QosDefaultUserPriEntry
	   MAX-ACCESS  not-accessible
	   STATUS      current
	   DESCRIPTION
	     "A table that contains information about every port that
	     is associated with this transparent bridge."
	   ::= { qosDefaultUserPri 1 }
	
	qosDefaultUserPriEntry OBJECT-TYPE
	   SYNTAX      QosDefaultUserPriEntry
	   MAX-ACCESS  not-accessible
	   STATUS      current
	   DESCRIPTION
	     "A list of Default User Priorities for each port of a
	     transparent bridge.  This is indexed by dot1dBasePort."
	   INDEX { qosDefaultUserPriPortIndex }
	   ::= { qosDefaultUserPriTable 1 }
	
	QosDefaultUserPriEntry ::=
	   SEQUENCE {
			  qosDefaultUserPriPortIndex
				 INTEGER,
	          qosDefaultUserPriority
	             INTEGER
	}
	
	qosDefaultUserPriPortIndex OBJECT-TYPE
	   SYNTAX      INTEGER   (1..28)
	   MAX-ACCESS  read-only
	   STATUS      current
	   DESCRIPTION
	     "The shown index for default user priority, the real index
		 is dot1dBasePort."
	   ::= { qosDefaultUserPriEntry 1 }
	
	qosDefaultUserPriority OBJECT-TYPE
	   SYNTAX      INTEGER {
	   						level0(0),
							level1(1),
							level2(2),
							level3(3),
							level4(4),
							level5(5),
							level6(6),
							level7(7)
						}
	   MAX-ACCESS  read-write
	   STATUS      current
	   DESCRIPTION
	     "The default ingress User Priority for this port.  This
	     only has effect on media, such as Ethernet, that do not
	     support native User Priority."
		DEFVAL  {level0}
	   ::= { qosDefaultUserPriEntry 2 }

-- ipv6 traffic class
--    ipv6TrafficClassTable  OBJECT-TYPE
--        SYNTAX     SEQUENCE OF Ipv6TrafficClassEntry 
--        MAX-ACCESS not-accessible
--        STATUS     current
--        DESCRIPTION
--           "A list of cos configuration for queue class remapping or priority remark."

--        ::= { qosIP6TrafficClass 1 }

--    ipv6TrafficClassEntry OBJECT-TYPE
--        SYNTAX     Ipv6TrafficClassEntry
--        MAX-ACCESS not-accessible
--        STATUS     current
--        DESCRIPTION
--              "A list of cos configuration entry."

--        INDEX { ipv6TrafficClassIndex }
--        ::= { ipv6TrafficClassTable 1 }

--    Ipv6TrafficClassEntry  ::= 
--            SEQUENCE {
--              ipv6TrafficClassIndex          	Integer32,
--              ipv6TrafficClass   				Integer32,
--              ipv6TrafficClassPriority    		INTEGER,
--              ipv6TrafficClassStatus         	RowStatus
--              }
              
--    ipv6TrafficClassIndex OBJECT-TYPE
--       SYNTAX       Integer32 (1..65535)
--       MAX-ACCESS   read-only
--       STATUS       current
--       DESCRIPTION
--         "Index of cos configuration entry." 
--        ::= { ipv6TrafficClassEntry  1 }
		
--    ipv6TrafficClass OBJECT-TYPE
--       SYNTAX       Integer32  (0..255)
--       MAX-ACCESS   read-write
--       STATUS       current
--       DESCRIPTION
--         "Ipv6 traffic class of cos configuration." 
--        ::= { ipv6TrafficClassEntry  2 }

--    ipv6TrafficClassPriority OBJECT-TYPE
--	    SYNTAX      INTEGER  (0..7)
--       MAX-ACCESS   read-write
--       STATUS       current
--       DESCRIPTION
--         "Remapping queue class for matched packet." 
--        ::= { ipv6TrafficClassEntry  3 }
		
--    ipv6TrafficClassStatus OBJECT-TYPE
--       SYNTAX RowStatus
--       MAX-ACCESS read-write
---       STATUS current
--       DESCRIPTION
--         "Status of cos configuration entry."
--       ::= { ipv6TrafficClassEntry 4 } 
	   
--	ipv6TCGlobalStatus 	OBJECT-TYPE 
--		SYNTAX      INTEGER {
--				enabled(1),
--				disabled(2)
--				}
--		MAX-ACCESS  read-write 
--		STATUS      current 
--		DESCRIPTION 
--				"Enable/Disable ipv6 traffic class function."
--		DEFVAL  { 2 }
--		::= { qosIP6TrafficClass 2 }	  

-- Rate Control Group --------------------------------------------- --

	bandwidthCtrlTable OBJECT-TYPE 
		SYNTAX      SEQUENCE OF BandwidthCtrlEntry 
		MAX-ACCESS  not-accessible 
		STATUS      current 
		DESCRIPTION 
		   "A table to control the rate limiting parameters 
		    either for the entire switch or for each interface in the switch."
		::= { sysBandWidthCtrl 1 }

	bandwidthCtrlEntry OBJECT-TYPE 
	   SYNTAX      BandwidthCtrlEntry 
	   MAX-ACCESS  not-accessible 
	   STATUS      current 
	   DESCRIPTION 
	      "An entry appears in this table for each physical
	       interface in the switch."
	   INDEX { bandwidthCtrlIndex }
	   ::= { bandwidthCtrlTable 1 }
	   
	BandwidthCtrlEntry ::= 
	   SEQUENCE { 
	      bandwidthCtrlIndex 
	         Integer32, 
	      bandwidthCtrlTxThreshold
	         Integer32,
	      bandwidthCtrlRxThreshold
	         Integer32
	  }
	
	bandwidthCtrlIndex OBJECT-TYPE 
	   SYNTAX      Integer32   (1..28)
	   MAX-ACCESS  read-only 
	   STATUS      current 
	   DESCRIPTION 
	      "The interface index for which the configuration in this 
	       entry applies."
	   ::= { bandwidthCtrlEntry 1 }

	bandwidthCtrlTxThreshold OBJECT-TYPE
	   SYNTAX      Integer32 (0..15625)
	   MAX-ACCESS  read-write
	   STATUS      current
	   DESCRIPTION
          "Configures interface Rate Limit (Bits(In units of 64,000 bits per
          second) that can be transferred on a port at a particular second).

		  
	      This object's value will take effect on the interface speed. Based
	      on the operating speed of the port, the rate limit will be applied.
	      This value can also be affected by the metering. A value of zero(0)
	      disable rate limiting i.e. sets the port to full speed."

	   ::= { bandwidthCtrlEntry 2 }

	bandwidthCtrlRxThreshold OBJECT-TYPE
	   SYNTAX      Integer32 (0..15625)
	   MAX-ACCESS  read-write
	   STATUS      current
	   DESCRIPTION
          "Configures interface Rate Limit (Bits(In units of 64,000 bits per
          second) that can be transferred on a port at a particular second).
	
	      This object's value will take effect on the interface speed. Based
	      on the operating speed of the port, the rate limit will be applied.
	      This value can also be affected by the metering. A value of zero(0)
	      disable rate limiting i.e. sets the port to full speed."
	
	   ::= { bandwidthCtrlEntry 3 }



-- Storm Control
	stormCtrlTable OBJECT-TYPE
	   SYNTAX      SEQUENCE OF StormCtrlEntry
	   MAX-ACCESS  not-accessible
	   STATUS      current
	   DESCRIPTION
		  "A table to control the rate limiting parameters
		   either for the entire switch or for each interface in the switch."
	   ::= { sysStormCtrl 1 }

	stormCtrlEntry OBJECT-TYPE
	   SYNTAX      StormCtrlEntry
	   MAX-ACCESS  not-accessible
	   STATUS      current
	   DESCRIPTION
		  "An entry appears in this table for each physical
		   interface in the switch."
	   INDEX { stormCtrlIndex }
	   ::= { stormCtrlTable 1 }

	StormCtrlEntry ::=
	   SEQUENCE {
		  stormCtrlIndex
			 Integer32,
		  stormCtrlDlfOnOff
			 INTEGER,
		  stormCtrlBroadcastOnOff
			 INTEGER,
		  stormCtrlMulticastOnOff
			 INTEGER,
		  stormCtrlThreshold
		     INTEGER
	   }
	   
	stormCtrlIndex OBJECT-TYPE
	   SYNTAX      Integer32   (1..28)
	   MAX-ACCESS  read-only
	   STATUS      current
	   DESCRIPTION
		  "The interface index for which the configuration in this
		   entry applies."
	   ::= { stormCtrlEntry 1 }

	stormCtrlDlfOnOff       OBJECT-TYPE 
 		SYNTAX INTEGER  {
							enabled(1),
							disabled(2)
						}
		MAX-ACCESS  read-write 
		STATUS      current 
		DESCRIPTION 
			   "This object indicates unknown unicast storm control function is enabled or disabled 
				for device.
				When you enable unknown unicast storm control function, it
				will allowed you to limit the number of unknown unicast packets 
				per second going through device."
		DEFVAL  {2}
		::= { stormCtrlEntry 2 }

	stormCtrlBroadcastOnOff       OBJECT-TYPE 
 		SYNTAX INTEGER  {
							enabled(1),
							disabled(2)
						}
		MAX-ACCESS  read-write 
		STATUS      current 
		DESCRIPTION 
			   "This object indicates broadcast storm control function is enabled or disabled 
				for device.
				When you enable broadcast storm control function, it
				will allowed you to limit the number of broadcast packets 
				per second going through device.
				"
		DEFVAL  {2}
		::= { stormCtrlEntry 3 }
		
	stormCtrlMulticastOnOff       OBJECT-TYPE 
 		SYNTAX INTEGER  {
							enabled(1),
							disabled(2)
						}
		MAX-ACCESS  read-write 
		STATUS      current 
		DESCRIPTION 
			   "This object indicates multicast storm control function is enabled or disabled 
				for device.
				When you enable multicast storm control function, it
				will allowed you to limit the number of multicast packets 
				per second going through device."
		DEFVAL  {2}
		::= { stormCtrlEntry 4 }
		
			
	stormCtrlThreshold       OBJECT-TYPE 
 	   SYNTAX      INTEGER (1..22194)
	   MAX-ACCESS  read-write
	   STATUS      current
	   DESCRIPTION
          "Configures interface storm control threshold(Packets(In units of 64,000 packets per
          second) that can be transferred on a port at a particular second).
	
	      This object's value will take effect on the interface speed. Based
	      on the operating speed of the port, the threshold will be applied.
	      "
		DEFVAL  {22194}
		::= { stormCtrlEntry 5 }


	qosIP6TrafficClass OBJECT IDENTIFIER ::= { sysQoS 5 }
	
-- ipv6 traffic class
    ipv6TrafficClassTable  OBJECT-TYPE
        SYNTAX     SEQUENCE OF Ipv6TrafficClassEntry 
        MAX-ACCESS not-accessible
        STATUS     current
        DESCRIPTION
           "A list of cos configuration for queue class remapping or priority remark."

        ::= { qosIP6TrafficClass 1 }

    ipv6TrafficClassEntry OBJECT-TYPE
        SYNTAX     Ipv6TrafficClassEntry
        MAX-ACCESS not-accessible
        STATUS     current
        DESCRIPTION
              "A list of cos configuration entry."

        INDEX { ipv6TrafficClass }
        ::= { ipv6TrafficClassTable 1 }

    Ipv6TrafficClassEntry  ::= 
            SEQUENCE {
             -- ipv6TrafficClassIndex          	Integer32,
              ipv6TrafficClass   				Integer32,
              ipv6TrafficClassPriority    		INTEGER,
              ipv6TrafficClassStatus         	RowStatus
              }
              
--    ipv6TrafficClassIndex OBJECT-TYPE
--       SYNTAX       Integer32 (1..65535)
--       MAX-ACCESS   read-only
--       STATUS       current
--       DESCRIPTION
--         "Index of cos configuration entry." 
--        ::= { ipv6TrafficClassEntry  1 }
		
    ipv6TrafficClass OBJECT-TYPE
       SYNTAX       Integer32  (0..255)
       MAX-ACCESS   read-only
       STATUS       current
       DESCRIPTION
         "Ipv6 traffic class of cos configuration." 
        ::= { ipv6TrafficClassEntry  2 }

    ipv6TrafficClassPriority OBJECT-TYPE
	    SYNTAX      INTEGER  (0..7)
       MAX-ACCESS   read-write
       STATUS       current
       DESCRIPTION
         "Remapping queue class for matched packet." 
        ::= { ipv6TrafficClassEntry  3 }
		
    ipv6TrafficClassStatus OBJECT-TYPE
       SYNTAX RowStatus
       MAX-ACCESS read-write
       STATUS current
       DESCRIPTION
         "Status of cos configuration entry."
       ::= { ipv6TrafficClassEntry 4 } 
	   
	ipv6TCGlobalStatus 	OBJECT-TYPE 
		SYNTAX      INTEGER {
				enabled(1),
				disabled(2)
				}
		MAX-ACCESS  read-write 
		STATUS      current 
		DESCRIPTION 
				"Enable/Disable ipv6 traffic class function."
		DEFVAL  { 2 }
		::= { qosIP6TrafficClass 2 }	  
	

-- sysIPv6SysSettings
    ipv6GlobalStatus  OBJECT-TYPE
       SYNTAX      INTEGER {
						enabled(1),
						disabled(2)
	   }
       MAX-ACCESS  read-write
       STATUS      current
       DESCRIPTION 
          "This object is to enable/disable ipv6 function of system."
	   DEFVAL { disabled }
       ::= { sysIPv6SysSettings 1 }

	ipv6DHCPClientStatus  OBJECT-TYPE
       SYNTAX      INTEGER {
						enabled(1),
						disabled(2)
		}
       MAX-ACCESS  read-write
       STATUS      current
       DESCRIPTION 
          "This object is to set the status of dhcpv6 client status.
		   when enabled, ipv6 global unicast address will be assigned by
		   dhcpv6 server. Otherwise by mannaul."
	   DEFVAL{ disabled }
       ::= { sysIPv6SysSettings 2 }

	ipv6AutolinkloStatus  OBJECT-TYPE
       SYNTAX      INTEGER {
						enabled(1),
						disabled(2)
	   }
       MAX-ACCESS  read-write
       STATUS      current
       DESCRIPTION 
          "This object is to set the status of ipv6 link local address auto-generated.
		   if set enabled, system will auto-generate a link-local ipv6 address by switch 
		   base mac address. if set disabled, link-local address will be configured by manual."
	   DEFVAL{ disabled }
       ::= { sysIPv6SysSettings 4 }

	ipv6NSRetransmitTime  OBJECT-TYPE
       SYNTAX      Integer32 (1..3600)
       MAX-ACCESS  read-write
       STATUS      current
       DESCRIPTION 
          "The retransmit time to be indicated in the router 
			advertisements sent on this IPv6 default interface and also used by
			this entity. This defines the time in seconds between 
			retransmitted Neighbor Solicitations and is used during
			address resolution, unreachability detection and
			duplicate address detection."
	   DEFVAL {1}
       ::= { sysIPv6SysSettings 5 }

	ipv6StaticGateway  OBJECT-TYPE
       SYNTAX      OCTET STRING
       MAX-ACCESS  read-write
       STATUS      current
       DESCRIPTION 
          "The ipv6 default gateway that you want the default interface to be in"
       ::= { sysIPv6SysSettings 6 }

	   
	ipv6DynamicGateway  OBJECT-TYPE
       SYNTAX      OCTET STRING
       MAX-ACCESS  read-only
       STATUS      current
       DESCRIPTION 
          "The ipv6 default gateway that was derived from a configured address prefix."
       ::= { sysIPv6SysSettings 7 }

		  
-- ipv6IpAddrTable begin
		 ipv6IpAddrTable   OBJECT-TYPE
              SYNTAX   SEQUENCE OF Ipv6IpAddrEntry
              MAX-ACCESS   not-accessible
              STATUS   current
              DESCRIPTION
                 "The table containing entity's IPv6 addressing information."
              ::= { sysIPv6SysSettings 10 }


          ipv6IpAddrEntry   OBJECT-TYPE
              SYNTAX   Ipv6IpAddrEntry
              MAX-ACCESS   not-accessible
              STATUS   current
              DESCRIPTION
                 "The entry in the IPv6 Address Table which defines a
                 unicast or link-local address on an IPv6 interface."
              INDEX  {ipv6IpAddrIndex,
                      ipv6IpAddrAddress,
                      ipv6IpAddrPrefixLen
                     }
              ::= { ipv6IpAddrTable 1 }


          Ipv6IpAddrEntry  ::=
              SEQUENCE {
                 ipv6IpAddrIndex
                     InterfaceIndex,
                 ipv6IpAddrAddress
                     Ipv6Address,
                 ipv6IpAddrPrefixLen
                     Integer32,
                 ipv6IpAddrType
                     INTEGER,				
                 ipv6IpAddrRowStatus
                     RowStatus
              }


          ipv6IpAddrIndex OBJECT-TYPE
              SYNTAX   InterfaceIndex
              MAX-ACCESS  read-only
              STATUS   current
              DESCRIPTION
                 "The index value which uniquely identifies the IPv6
                 interface on which this IPv6 address entry exists."
              ::= { ipv6IpAddrEntry 1 }


          ipv6IpAddrAddress OBJECT-TYPE
              SYNTAX   Ipv6Address
              MAX-ACCESS   read-only
              STATUS   current
              DESCRIPTION
                 "The IPv6 address to which this entry's addressing
                  information pertains."
              ::= { ipv6IpAddrEntry 2 }


          ipv6IpAddrPrefixLen OBJECT-TYPE
              SYNTAX   Integer32 (1..128)
              MAX-ACCESS  read-only
              STATUS   current
              DESCRIPTION
                 "The length of the prefix (in bits) associated with
                 the IPv6 address of this entry. For a link-local address,
                 the prefix is always start with '0xfe80' and the prefix
                 length is 128 bits."
              ::= { ipv6IpAddrEntry 3 }
     

          ipv6IpAddrType OBJECT-TYPE
              SYNTAX   INTEGER {
                            unicast(1),
--                            anycast(2),
                            linklocal(3)
                       }
              MAX-ACCESS   read-only
              STATUS   current
              DESCRIPTION
                "Indicates whether the address is a unicast or
                 link-local address. Syntactically there is no difference
                 between a unicast address and a anycast address while a
                 link-local address has the prefix '0xfe80'."
                   
                   ::= { ipv6IpAddrEntry 5 }  

          ipv6IpAddrRowStatus OBJECT-TYPE
              SYNTAX            RowStatus
              MAX-ACCESS   read-create
              STATUS   current
              DESCRIPTION
                "Indicates the desired status of the address. Also a creation
                 of an address can trigger IPv6 to be enabled over the
                 interface. Similarly deletion of all the address may trigger
                 IPv6 to be disabled on the interface. NotInService value is
                 not supported."
              ::= { ipv6IpAddrEntry 6 }


-- sysIPv6Neighbor
        -- IPv6 Address Translation table for LAN interfaces

         -- The fsipv6NdLanCacheTable contain the Ipv6Address
         -- to `physical' address equivalences for on-link nodes
         -- on Ethernet. 
         -- Static entries can be created/deleted from SNMP. Dynamic
         -- entries get created for neighbors upon IPv6 packet forwarding.


         ipv6NeighborTable OBJECT-TYPE
             SYNTAX      SEQUENCE OF Ipv6NeighborEntry
             MAX-ACCESS      not-accessible
             STATUS      current
             DESCRIPTION
               "The IPv6 Address Translation table used for
               mapping from IPv6 addresses to physical addresses
               on Ethernet."
             ::= { sysIPv6Neighbor 1 }


         ipv6NeighborEntry OBJECT-TYPE
             SYNTAX     Ipv6NeighborEntry
             MAX-ACCESS     not-accessible
             STATUS     current
             DESCRIPTION
               "Each entry contains one IPv6 address to `physical'
               address equivalence. Entries are created dynamically upon
               address resolution or statically from SNMP."
             INDEX   { ipv6NeighborIfIndex,
                       ipv6NeighborIpv6Addr }
             ::= { ipv6NeighborTable 1 }


         Ipv6NeighborEntry ::= 
             SEQUENCE {
                 ipv6NeighborIfIndex
                     InterfaceIndex,
                 ipv6NeighborIpv6Addr
                     Ipv6Address,
                 ipv6NeighborMACAddr
                     OCTET STRING,
                 ipv6NeighborCacheState
                     INTEGER,
		  ipv6NeighborInterfaceName
		      DisplayString,
                 ipv6NeighborRowStatus
                     INTEGER
             }


          ipv6NeighborIfIndex OBJECT-TYPE
              SYNTAX   InterfaceIndex
              MAX-ACCESS    read-only
              STATUS   current
              DESCRIPTION
                "The index value which uniquely identifies the IPv6
                 interface on which this ipv6Neighborentry exists.
                 The interface be must existed."
              ::= { ipv6NeighborEntry 1 }


         ipv6NeighborIpv6Addr OBJECT-TYPE
             SYNTAX     Ipv6Address
             MAX-ACCESS   read-only
             STATUS     current
             DESCRIPTION
               "The IPv6 Address corresponding to the `physical' address
                on Ethernet."
             ::= { ipv6NeighborEntry 2 }


         ipv6NeighborMACAddr OBJECT-TYPE
             SYNTAX     OCTET STRING (SIZE (6))
             MAX-ACCESS     read-write
             STATUS     current
             DESCRIPTION
               "The `physical' address on Ethernet."
             ::= { ipv6NeighborEntry 3 }


         ipv6NeighborCacheState OBJECT-TYPE
             SYNTAX     INTEGER {
                         static(1),
                         dynamic(2)
                        }
             MAX-ACCESS     read-only
             STATUS     current
             DESCRIPTION
              "The object indicates whether the neighbor cache is created manually or learnt dynamically."
             ::= { ipv6NeighborEntry 4 }
			 
		 ipv6NeighborInterfaceName OBJECT-TYPE
			 SYNTAX      DisplayString (SIZE (0..32))
			 MAX-ACCESS  read-only
			 STATUS      current
			 DESCRIPTION
					"This object indicates the name of the IPv6 interface."
			 ::= { ipv6NeighborEntry 5 }


         ipv6NeighborRowStatus OBJECT-TYPE
             SYNTAX     INTEGER  {
                          valid (1),
                          invalid(2)
                        }
             MAX-ACCESS     read-write
             STATUS     current
             DESCRIPTION
              "Setting this object to the value invalid(2)
               effects in invalidating the corresponding entry
               in the ipv6NeighborTable. Otherwise, the entry
               remains valid."
             DEFVAL  { valid }
             ::= { ipv6NeighborEntry 6 }

		
   -- --------------------------------------------------------------
   -- The Guest VLAN Table 
   -- --------------------------------------------------------------
   
	pnacGuestVlanTable OBJECT-TYPE
	   SYNTAX      SEQUENCE OF TabPnacGuestVlanEntry
	   MAX-ACCESS  not-accessible
	   STATUS      current
	   DESCRIPTION
		  "This table contains authentication session information
		   associated with each Guest vlan  while Authenticator
		   operates in port based authentication mode."
	   ::= { sysPNAC 6 }

	pnacGuestVlanEntry OBJECT-TYPE
	   SYNTAX      TabPnacGuestVlanEntry
	   MAX-ACCESS  not-accessible
	   STATUS      current
	   DESCRIPTION
		  "Guest Vlan ID assign with each port."
	   INDEX { pnacPaePortIndex }
	   ::= { pnacGuestVlanTable 1 }

	TabPnacGuestVlanEntry ::=
	   SEQUENCE {
		  pnacPaePortIndex
			  Integer32,
		  pnacGuestVlanId
			  Integer32

	   }

	pnacPaePortIndex OBJECT-TYPE
	   SYNTAX      Integer32   (1..28)
	   MAX-ACCESS  read-only
	   STATUS      current
	   DESCRIPTION
		  "The port number associated with this port."
	   ::= { pnacGuestVlanEntry 1 }
	   
	pnacGuestVlanId OBJECT-TYPE
	   SYNTAX      Integer32
	   MAX-ACCESS  read-write
	   STATUS      current
	   DESCRIPTION
		  "specify the guest vlan tag.0 for non exiting"
	   ::= { pnacGuestVlanEntry 2}		

	-- -------------------------------------------------------------
	-- acl Function
	-- ------------------------------------------------------------- 
--	aclRatelimit              		OBJECT IDENTIFIER ::= { sysACL 1 }
	aclPolicy    					OBJECT IDENTIFIER ::= { sysACL 1 }	
--  aclFreeCount              		OBJECT IDENTIFIER ::= { sysACL 3 }
	
	-- -------------------------------------------------------------
    -- acl profile action 
    -- -------------------------------------------------------------
--	aclRatelimitTable OBJECT-TYPE
--	   SYNTAX        SEQUENCE OF AclRatelimitEntry
--	   MAX-ACCESS    not-accessible
--	   STATUS        current
--	   DESCRIPTION
--		  "ACL rate limit entry table."
--	   ::= { aclRatelimit 1 }

--	aclRatelimitEntry OBJECT-TYPE
--	   SYNTAX       AclRatelimitEntry
--	   MAX-ACCESS   not-accessible
--	   STATUS       current
--	   DESCRIPTION  
--		  "Rate limit is used to assign a committed rate and a burst size"      
--	   INDEX { aclRatelimitIndex }
--	   ::= { aclRatelimitTable 1 }

--	AclRatelimitEntry ::=
--	   SEQUENCE {
--			aclRatelimitIndex					 Integer32,  
--			aclRatelimitCommittedRate			 Integer32,	 
--			aclRatelimitRowStatus				 RowStatus
--	   }
	   
--	aclRatelimitIndex OBJECT-TYPE
--	   SYNTAX        Integer32 (1..65535)
--	   MAX-ACCESS    read-only
--	   STATUS    current
--	   DESCRIPTION
--		  "The index of the Rate limit entry."
--	   ::=  { aclRatelimitEntry 1 }
--	aclRatelimitCommittedRate OBJECT-TYPE
--	   SYNTAX        Integer32 (1..15625)
--	   MAX-ACCESS    read-write
--	   STATUS    current
--	   DESCRIPTION
--		  "Committed rate in N*64Kbps. N is in the range 1~15625."
--	   ::=  { aclRatelimitEntry 2 }
	   
--	aclRatelimitRowStatus OBJECT-TYPE
--	   SYNTAX    RowStatus
--	   MAX-ACCESS   read-create
--	   STATUS    current
--	   DESCRIPTION
--		  "The row status of the entry.
--		   1: write - enable the entry 
--			  read - entry is enabled   
--		   2: write - disable the entry
--			  read - entry is disabled
--		   3: read - entry is not ready
--		   5: write - create the entry
--		   6: write - delete the entry"
--	   ::= { aclRatelimitEntry 3 }     
	
	-- -------------------------------------------------------------
    -- acl Policy group
    -- -------------------------------------------------------------	
	aclPolicyTable  OBJECT-TYPE
		SYNTAX     SEQUENCE OF AclPolicyEntry
        MAX-ACCESS not-accessible
        STATUS     current
        DESCRIPTION
			"A table to configure policy rules in the system."
		::= { aclPolicy 1 }

	aclPolicyEntry OBJECT-TYPE
        SYNTAX     AclPolicyEntry
        MAX-ACCESS not-accessible
        STATUS     current
        DESCRIPTION
              "Each entry in this table is a L3 filter rule.
         Index to the table is L3 filter number. "
        INDEX { aclPolicyIndex }
        ::= { aclPolicyTable 1 }

	AclPolicyEntry ::=
            SEQUENCE {
              aclPolicyIndex                		Integer32,              
              aclPolicySrcMac                   	MacAddress,
			  aclPolicySrcMacMaskLen             	Integer32,
			  aclPolicyDstMac           			MacAddress,
			  aclPolicyDstMacMaskLen    			Integer32,              
              aclPolicyVlanId                   	Integer32,
			  aclPolicy1pPriority             		Integer32,
			  aclPolicyEtherType          			Integer32,
			  aclPolicyTrafficClass      			Integer32,
			  aclPolicyIpType						INTEGER,
              aclPolicySrcIp                   		InetAddress,
			  aclPolicySrcIpMaskLen             	InetAddressPrefixLength,
			  aclPolicyDstIp           				InetAddress,
			  aclPolicyDstIpMaskLen    				InetAddressPrefixLength,              
              aclPolicyDscp                   		Integer32,
			  aclPolicyProtocol             		Integer32,
			  aclPolicySrcPort           			Integer32,
			  aclPolicyDstPort    					Integer32,
			  aclPolicyAction    					INTEGER,
			  aclPolicyReplaceDSCP    				Integer32,
			  aclPolicyReplaceCos    				Integer32,
--			  aclPolicyRateLimit    				Unsigned32,
			  aclPolicyPortList    					PortList,
			  aclPolicyEnable						INTEGER,
			  aclPolicyRowStatus   					RowStatus
            }

	aclPolicyIndex OBJECT-TYPE 
	   SYNTAX      Integer32  (1..65535)
	   MAX-ACCESS  read-only 
	   STATUS      current 
	   DESCRIPTION 
		  "Policy rule number."
	   ::= { aclPolicyEntry 1 }

	aclPolicySrcMac OBJECT-TYPE
	   SYNTAX        MacAddress
	   MAX-ACCESS    read-write
	   STATUS    current
	   DESCRIPTION
		  "Source MAC address."
	   ::=  { aclPolicyEntry 2 } 
		
	aclPolicySrcMacMaskLen OBJECT-TYPE
	   SYNTAX        Integer32 (0..48)
	   MAX-ACCESS    read-write
	   STATUS    current
	   DESCRIPTION
		  "Source MAC mask length.
			1-48: length in bits
			0: Ignored"      
	   ::=  { aclPolicyEntry 3 } 
	
	aclPolicyDstMac OBJECT-TYPE
	   SYNTAX        MacAddress
	   MAX-ACCESS    read-write
	   STATUS    current
	   DESCRIPTION
		  "Destincmon MAC address."
	   ::=  { aclPolicyEntry 4 } 

	aclPolicyDstMacMaskLen OBJECT-TYPE
	   SYNTAX        Integer32 (0..48)
	   MAX-ACCESS    read-write
	   STATUS    current
	   DESCRIPTION
		  "Destincmon MAC mask length.
			1-48: length in bits
			0: Ignored"      
	   ::=  { aclPolicyEntry 5 } 
  
	aclPolicyVlanId OBJECT-TYPE
	   SYNTAX        Integer32 (0..4093)
	   MAX-ACCESS    read-write
	   STATUS    current
	   DESCRIPTION
		  "802.1Q Vlan Id.
			1-4093: Vlan Id
			0: Ignored"	  
	   ::=  { aclPolicyEntry 6 } 
   
	aclPolicy1pPriority OBJECT-TYPE
	   SYNTAX        Integer32 (-1..7)
	   MAX-ACCESS    read-write
	   STATUS    current
	   DESCRIPTION
		  "802.1p priority. 
			0-7: 802.1p priority value      
			-1: Ignored"	  
	   ::=  { aclPolicyEntry 7 } 
   
	aclPolicyEtherType OBJECT-TYPE
	   SYNTAX        Integer32 (0..65535)
	   MAX-ACCESS    read-write
	   STATUS    current
	   DESCRIPTION
		  "EtherType. 
			0-65535: EtherType number 
			0: Ignored"	  
	   ::=  { aclPolicyEntry 8 } 
   
    aclPolicyTrafficClass OBJECT-TYPE 
	   SYNTAX      Integer32  (-1..255)
	   MAX-ACCESS  read-write 
	   STATUS      current 
	   DESCRIPTION 
		  "IPV6 traffic class for matched packet, it is used in COS.By Default, the value
		  will be '-1', which means the rule don't care this condition."
	  DEFVAL  { -1 }
	   ::= { aclPolicyEntry 9 } 
	
	aclPolicyIpType OBJECT-TYPE	
	SYNTAX INTEGER {
				ipv4 (1),
				ipv6 (2)
			}
    MAX-ACCESS     read-write
    STATUS         current
    DESCRIPTION
       "The type of IP address used by this classifier entry.  While
       other types of addresses are defined in the InetAddressType

       textual convention, and DNS names, a classifier can only look at
       packets on the wire. Therefore, this object is limited to IPv4
       and IPv6 addresses."
    ::= { aclPolicyEntry 10 }
			
	aclPolicySrcIp OBJECT-TYPE
	   SYNTAX         InetAddress
	   MAX-ACCESS     read-create
	   STATUS         current
	   DESCRIPTION
		   "The IP address to match against the packet's source IP address.
		   This may not be a DNS name, but may be an IPv4 or IPv6 prefix.
		   aclClassifierSrcIpMaskLen indicates the number of
		   bits that are relevant."
	   ::= { aclPolicyEntry 11 }
	
	aclPolicySrcIpMaskLen OBJECT-TYPE
		SYNTAX         InetAddressPrefixLength
		UNITS          "bits"
		MAX-ACCESS     read-create
		STATUS         current
		DESCRIPTION

		   "The length of the CIDR Prefix carried in
		   issAclPolicySrcIpAddr. In IPv4 addresses, a length of 0
		   indicates a match of any address; a length of 32 indicates a
		   match of a single host address, and a length between 0 and 32
		   indicates the use of a CIDR Prefix. IPv6 is similar, except that
		   prefix lengths range from 0..128."
		DEFVAL         { 0 }
		::= { aclPolicyEntry 12 }
	
	aclPolicyDstIp OBJECT-TYPE
		SYNTAX         InetAddress
		MAX-ACCESS     read-create
		STATUS         current
		DESCRIPTION
		   "The IP address to match against the packet's destination IP
		   address. This may not be a DNS name, but may be an IPv4 or IPv6
		   prefix.  aclClassifierDstIpMaskLen indicates the
		   number of bits that are relevant."
		::= { aclPolicyEntry 13 }

	aclPolicyDstIpMaskLen OBJECT-TYPE
		SYNTAX         InetAddressPrefixLength
		UNITS          "bits"
		MAX-ACCESS     read-create
		STATUS         current
		DESCRIPTION
		   "The length of the CIDR Prefix carried in
		   aclPolicyDstIpAddr. In IPv4 addresses, a length of 0
		   indicates a match of any address; a length of 32 indicates a
		   match of a single host address, and a length between 0 and 32
		   indicates the use of a CIDR Prefix. IPv6 is similar, except that
		   prefix lengths range from 0..128."
		DEFVAL         { 0 }
		::= { aclPolicyEntry 14 }
	
	aclPolicyDscp		OBJECT-TYPE
		SYNTAX		Integer32 (-1..63)
		MAX-ACCESS	read-create
		STATUS		current
		DESCRIPTION
			" The IP Dscp value to be checked against the packet. 
			A value of '-1' means, the Dscp Field becomes dont care."
		DEFVAL	{ -1 }
		::= { aclPolicyEntry 15 }
		
	aclPolicyProtocol OBJECT-TYPE 
	   SYNTAX      Integer32 (0..255)
	   MAX-ACCESS  read-write 
	   STATUS      current 
	   DESCRIPTION 
		  " The type of protocol to be checked against the packet. The
		  default value is 0. If the value is 0, it means that the
		  protocol type can be anything and it will not be checked to 
		  decide the action. "
	   DEFVAL   { 0 }
	   ::= { aclPolicyEntry 16 }
   
	aclPolicySrcPort OBJECT-TYPE
		SYNTAX      Integer32 (0..65535)
		MAX-ACCESS  read-write
		STATUS      current
		DESCRIPTION
			"The TCP / UDP source port. The default value is 0, 
			which means the rule don't care this condition."
		DEFVAL   { 0 }
		::= { aclPolicyEntry 17 }
	
	aclPolicyDstPort OBJECT-TYPE
		SYNTAX      Integer32 (0..65535)
		MAX-ACCESS  read-write
		STATUS      current
		DESCRIPTION
			"The TCP / UDP destination port. The default value is 0, 
			which means the rule don't care this condition."
		DEFVAL   { 0 }
		::= { aclPolicyEntry 18 }
	
	aclPolicyAction OBJECT-TYPE 
	   SYNTAX      INTEGER {
					  permit (1),
					  deny  (2)
				   }
	   MAX-ACCESS  read-write 
	   STATUS      current 
	   DESCRIPTION 
		  "Specifies the action to be taken on the packet if the filter
		  rule matches.
		  If the action is 'Permit', the packet will be forwarded according
		  to the forwarding rules.
		  If the action is 'Deny', the packet will be discarded."
	   DEFVAL  { permit } 
	   ::= { aclPolicyEntry 19 }
		
	aclPolicyReplaceDSCP	 OBJECT-TYPE
		SYNTAX      Integer32 (-1..63)
		MAX-ACCESS  read-write 
		STATUS      current 
		DESCRIPTION 
			"ReplaceDSCP for matched packet.When aclPolicyReplaceDSCP was set to one of 0~63, 
					then aclPolicyReplaceCos will be reset to -1." 
		DEFVAL  { -1 }       

	   ::= { aclPolicyEntry 20 }
   
    aclPolicyReplaceCos OBJECT-TYPE 
	   SYNTAX      Integer32  (-1..7)
	   MAX-ACCESS  read-write 
	   STATUS      current 
	   DESCRIPTION 
		  "802.1p priority for matched packet. By Default, the value
		  will be '-1', which means the rule don't care this condition.
		  When aclPolicyReplaceCos was set to one of 0~7, 
					then aclPolicyReplaceDSCP will be reset to -1."
	   DEFVAL  { -1 }
	   ::= { aclPolicyEntry 21 }  
	   
--	aclPolicyRateLimit OBJECT-TYPE 
--	   SYNTAX      Unsigned32 (1..65535)
--	   MAX-ACCESS  read-write 
--	   STATUS      current 
--	   DESCRIPTION 
--		  "Rate limit for matched packet."
--	   ::= { aclPolicyEntry 23 }	
	   
	aclPolicyPortList OBJECT-TYPE 
	   SYNTAX      PortList
	   MAX-ACCESS  read-write 
	   STATUS      current 
	   DESCRIPTION 
		  "Specifies the complete set of ports over which if the packet arrives
		  this filter rule will be applicable.
		  If the incoming port list is '0', the filter rule is applicable for all the 
		  incoming ports.

		  By default inport list is maintained as '0'." 
	   ::= { aclPolicyEntry 22 }

	aclPolicyEnable OBJECT-TYPE
	SYNTAX      INTEGER {
				enabled(1),
				disabled(2)
				}
	MAX-ACCESS    read-write
	STATUS    current
	DESCRIPTION
	  "The object enable/disable acl policy."	  
	::=  { aclPolicyEntry 23 } 
	
	aclPolicyRowStatus OBJECT-TYPE 
	   SYNTAX      RowStatus
	   MAX-ACCESS  read-create 
	   STATUS      current 
	   DESCRIPTION 
			"This object indicates the status of this entry. An entry is
			created in this table when this object is SET to 'createAndWait'.
			The entry in this table is used when the status of this object 
			is SET 'active'. The entry in this table is not used when this 
			object is SET 'notInService'. An entry created in this table is
			be deleted when this object is SET 'destroy'."
	   ::= { aclPolicyEntry 24 }   

    -- -------------------------------------------------------------
    -- acl profile action 
    -- -------------------------------------------------------------
--	aclFreeRuleCountInHw OBJECT-TYPE 
--	   SYNTAX      INTEGER
--	   MAX-ACCESS  read-only
--	   STATUS      current 
--	   DESCRIPTION 
--		  "This object provides ser defined ACL free rules from hardware,
--		  L2, L3, voice vlan, destination mac filter, IPV6 traffic class etc. share hardware PCL."
--	   ::= { aclFreeCount 1 } 

--	aclFreeRatelimitCountInHw OBJECT-TYPE 
--	   SYNTAX      INTEGER
--	   MAX-ACCESS  read-only
--	   STATUS      current 
--	   DESCRIPTION 
--		  "This object provides per defined ratelimit free entries from hardware,
--		  bandwidth, safeguard, and acl ratelimit share ratelimt."
--	   ::= { aclFreeCount 2 } 


	-- -------------------------------------------------------------
	-- Destination MAC Filter Function
	-- ------------------------------------------------------------- 
	
	-- -------------------------------------------------------------
    -- Destination MAC Filter group
    -- -------------------------------------------------------------
	macFilterTable  OBJECT-TYPE
		SYNTAX     SEQUENCE OF MacFilterEntry
        MAX-ACCESS    not-accessible
		STATUS        current
		DESCRIPTION
			"DstMacFilter entry table."
		::= { sysMACFilter 1 }

	macFilterEntry OBJECT-TYPE
	   SYNTAX       MacFilterEntry
	   MAX-ACCESS   not-accessible
	   STATUS       current
	   DESCRIPTION
		  "DstMacFilter is used to filter the packets by the specific Destination MAC."
	   INDEX { macFilterIndex }
	   ::= { macFilterTable 1 }

	MacFilterEntry ::=
	   SEQUENCE {
			macFilterIndex			 	 Integer32,  
			macFilterAddress			 MacAddress,		 	  
			macFilterRowStatus			 RowStatus
	   }
	   
	macFilterIndex OBJECT-TYPE
	   SYNTAX        Integer32 (1..40)
	   MAX-ACCESS    read-only
	   STATUS    current
	   DESCRIPTION
		  "The index of the DstMacFilter entry."
	   ::=  { macFilterEntry 1 }

	macFilterAddress OBJECT-TYPE
	   SYNTAX        MacAddress
	   MAX-ACCESS    read-write
	   STATUS    current
	   DESCRIPTION
		  "Destnation MAC address"
	   ::=  { macFilterEntry 2 }

	macFilterRowStatus OBJECT-TYPE
	   SYNTAX    RowStatus
	   MAX-ACCESS   read-create
	   STATUS    current
	   DESCRIPTION
		  "The row status of the entry.
		   1: write - enable the entry 
			  read - entry is enabled   
		   2: write - disable the entry
			  read - entry is disabled
		   3: read - entry is not ready
		   5: write - create the entry
		   6: write - delete the entry"
	   ::= { macFilterEntry 3 }
  

	-- -------------------------------------------------------------
	-- link aggregation Function
	-- ------------------------------------------------------------- 
	laSystem    				OBJECT IDENTIFIER ::= { sysLA 1 }
	laPortChannel    			OBJECT IDENTIFIER ::= { sysLA 2 }
	laPort						OBJECT IDENTIFIER ::= { sysLA 3 }

    -- -------------------------------------------------------------
    -- link aggregation system group
    -- -------------------------------------------------------------
	laActorSystemID OBJECT-TYPE
       	SYNTAX      MacAddress
       	MAX-ACCESS  read-only
       	STATUS      current
       	DESCRIPTION
           	"A 6-octet read-only MAC address value used as a unique
			identifier for the System."
		::= { laSystem 1 }

  	laSystemPriority OBJECT-TYPE
		SYNTAX      INTEGER (0..65535)
       	MAX-ACCESS  read-only
       	STATUS      current
       	DESCRIPTION
           	"The priority value assigned to System.
            This 16-bit value is read-only."
		::= { laSystem 2 }
	
	-- -------------------------------------------------------------
    -- link aggregation port channel group
    -- -------------------------------------------------------------
	laPortChannelTable  OBJECT-TYPE
		SYNTAX     SEQUENCE OF LaPortChannelEntry
        MAX-ACCESS not-accessible
        STATUS     current
        DESCRIPTION
			"A Port-channel is created through ifMain table.
           	After the creation of the port-channel, corresponding logical
           	interface will be created in the ifMain table. 
           	This Port-channel table is indexed through Key values and allows to 
           	configure link selection policy and the Mac address for 
           	the port-channel. All other objects in this table displays 
           	the details of the port-channel"
		::= { laPortChannel 1 }

	laPortChannelEntry OBJECT-TYPE
        SYNTAX     LaPortChannelEntry
        MAX-ACCESS not-accessible
        STATUS     current
        DESCRIPTION
              "There is one entry in this table for each created port-channel port"
        INDEX { laPortChannelIfIndex }
        ::= { laPortChannelTable 1 }

	LaPortChannelEntry ::=
            SEQUENCE {
              laPortChannelIfIndex                	InterfaceIndex,              
              laPortChannelMode                   	INTEGER,
			  laPortChannelMemberList             	PortList,
			  laPortChannelActivePortList           PortList,
			  laPortChannelStandbyPortList        	PortList
            }

	laPortChannelIfIndex OBJECT-TYPE
        SYNTAX      InterfaceIndex
        MAX-ACCESS  read-only
        STATUS      current
        DESCRIPTION
              "The ifIndex of the port-channel(Aggregator's interface index). "
        ::= { laPortChannelEntry 1 }

	laPortChannelMode OBJECT-TYPE
		SYNTAX INTEGER  {
    		 active(1),
    		 passive(2),
			 manual(3),
			 disabled(4)
        }
       	MAX-ACCESS   read-write
       	STATUS       current
       	DESCRIPTION
         	"Current Operating Channel Mode of the port	
				active(1)    - it will always send frames along the configured links.
				passive(2)   - If the actor and partner are both in passive mode, they do not 
								exchange LACP packets.				
				manual(3)  - force the port to enable channeling (Manual).
				disabled(4) - channeling is disabled."
				 
				
		::= { laPortChannelEntry 2 }
		
	laPortChannelMemberList OBJECT-TYPE
        SYNTAX      PortList
        MAX-ACCESS  read-write
        STATUS      current
        DESCRIPTION
              "Member Port list of the port channel. Add the ports as a 
	        aggregation member associated of a port-channel."
        ::= { laPortChannelEntry 3 }
	
	laPortChannelActivePortList OBJECT-TYPE
        SYNTAX      PortList
        MAX-ACCESS  read-only
        STATUS      current
        DESCRIPTION
              "This object will give the member Port list that are attached to the 
				port-channel and actively carrying data traffic on the link."
        ::= { laPortChannelEntry 4 }
	
	laPortChannelStandbyPortList OBJECT-TYPE
	   SYNTAX       PortList
	   MAX-ACCESS   read-only
	   STATUS       current
	   DESCRIPTION
	       "This object will give the port list that are standby due to 
         port-channel have attach port limitation."
	   ::= { laPortChannelEntry 5 }	

    -- -------------------------------------------------------------
    -- link aggregation port control group
    -- -------------------------------------------------------------
	laPortTable OBJECT-TYPE
		SYNTAX SEQUENCE OF LaPortEntry
      	MAX-ACCESS         not-accessible
      	STATUS             current
      	DESCRIPTION
         	"A table that contains objects to set the port lacp mode
         	of laPortTable."
		::={laPort 1 }

	laPortEntry OBJECT-TYPE
		SYNTAX      LaPortEntry
		MAX-ACCESS  not-accessible
		STATUS      current
		DESCRIPTION
         	"Each entry in this table is for each physical port that participates 
         	in Link Aggregation which can be either aggregatable or individual.
         	This table is indexed by the PortIndex."
		INDEX {laPortIndex }
		::={laPortTable 1 }

	LaPortEntry ::=
		SEQUENCE {
			laPortIndex                         InterfaceIndex,
         	laPortActorPortPriority             INTEGER
        }

	laPortIndex OBJECT-TYPE
		SYNTAX     InterfaceIndex
      	MAX-ACCESS read-only
      	STATUS     current
      	DESCRIPTION
         	"The Index of the port"
      	::={laPortEntry 1 }

	laPortActorPortPriority OBJECT-TYPE
		SYNTAX      INTEGER (0..65535)
      	MAX-ACCESS  read-write
      	STATUS      current
      	DESCRIPTION
       		"The priority value assigned to this Aggregation Port.
            This 16-bit value is read-write."
      	::={laPortEntry 2 }
  
	
   dosTable  OBJECT-TYPE
        SYNTAX  SEQUENCE OF DosEntry
        MAX-ACCESS  not-accessible
        STATUS  current
        DESCRIPTION
            "A table that holds the DoS prevention settings of the device."
        ::= { sysDos 1 }

    dosEntry OBJECT-TYPE
        SYNTAX  DosEntry
        MAX-ACCESS  not-accessible
        STATUS  current
        DESCRIPTION
            "A list of DoS prevention settings of the device."
        INDEX   { dosType }
        ::= { dosTable 1 }

    DosEntry ::= 
        SEQUENCE {
			dosType           INTEGER,
			dosState          INTEGER
        }
        
    dosType OBJECT-TYPE
    	SYNTAX INTEGER {
				land-attack(1),
				blat-attack(2),
				tcp-null-scan(3),
				tcp-xmascan(4),
				tcp-synfin(5),
				tcp-syn-srcport-less-1024(6),
				ping-death-attack(7),
				tcp-tiny-fragment(8)
   	    	}
        MAX-ACCESS  read-only
        STATUS current
        DESCRIPTION
            "This object indicates the DoS prevention type."
    ::= { dosEntry 1 }
    
	dosState OBJECT-TYPE
        SYNTAX INTEGER {
               deny(1),
               allow(2)
               }
        MAX-ACCESS  read-write
        STATUS  current
        DESCRIPTION
            "This object indicates the status of the DoS type.
			deny: 	Enable the DoS prevention;
			allow: 	Disable the DoS prevention."
	DEFVAL  { allow } 
    ::= { dosEntry 2 }
       
			
	
	dnsGlobal         OBJECT IDENTIFIER ::= { sysDNS 1 }
	
   -- Rmon System

	dnsNameServerIPv4Addr OBJECT-TYPE
		SYNTAX      OCTET STRING
		MAX-ACCESS  read-write
		STATUS      current
		DESCRIPTION 
			  "The Object represents the Name server's IPv4 Address."
		   ::= { dnsGlobal 1 }

	dnsNameServerIPv6Addr OBJECT-TYPE
		SYNTAX      OCTET STRING
		MAX-ACCESS  read-write
		STATUS      current
		DESCRIPTION 
			  "The Object represents the Name server's IPv6 Address."
		   ::= { dnsGlobal 2 }		   
			
          

END
